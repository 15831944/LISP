(sssetfirst nil (ssget "_X" '((0 . "DIMENSION"))))


(sssetfirst nil (ssget "_X" '((100 . "AcDbAlignedDimension,AcDbRotatedDimension"))))

(sssetfirst nil (ssget "_X" '((100 . "AcDb2LineAngularDimension"))))
AcDb2LineAngularDimension

(100 . "AcDbAlignedDimension,AcDbRotatedDimension")

(do #actdoc)


(setq dsts (vla-get-DimStyles #actdoc))

(setq dst2 (vla-item (vla-get-DimStyles #actdoc) 1))
(setq dst0 (vla-item (vla-get-DimStyles #actdoc) 2))

(do
  (vla-item
    (vla-get-DimStyles #actdoc)
    1)
  )


(vla-delete  (vla-item (vla-get-DimStyles #actdoc) 1))
; ошибка: Ошибка Automation. На объект ссылаются другие объекты



_$ (vlax-vla-object->ename dst0)
<Имя объекта: 78cb2a58>
_$ (entget (vlax-vla-object->ename dst0))

((-1 . <Имя объекта: 78cb2a58>)
  (0 . "DIMSTYLE")
  (105 . "117B")
  (102 . "{ACAD_REACTORS")
  (330 . <Имя объекта: 78675a50>)
  (330 . <Имя объекта: 786c3178>)
  (330 . <Имя объекта: 786c31a8>)
  (330 . <Имя объекта: 786c31c8>)
  (330 . <Имя объекта: 786c31e8>)
  (330 . <Имя объекта: 786c31f0>)
  (330 . <Имя объекта: 786c31f8>)
  (330 . <Имя объекта: 786c3218>)
  (330 . <Имя объекта: 786c3220>)
  (330 . <Имя объекта: 786c3228>)
  (330 . <Имя объекта: 786c3240>)
  (330 . <Имя объекта: 786c3248>)
  (330 . <Имя объекта: 786c3260>)
  (330 . <Имя объекта: 786c3270>)
  (330 . <Имя объекта: 786c32a0>)
  (330 . <Имя объекта: 786c32e0>)
  (330 . <Имя объекта: 786c32e8>)
  (330 . <Имя объекта: 786c32f0>)
  (330 . <Имя объекта: 786c32f8>)
  (330 . <Имя объекта: 786c3300>)
  (330 . <Имя объекта: 786c3308>)
  (330 . <Имя объекта: 786c3310>)
  (330 . <Имя объекта: 786c3318>)
  (330 . <Имя объекта: 786c3320>)
  (330 . <Имя объекта: 7861d028>)
  (330 . <Имя объекта: 7861d070>)
  (330 . <Имя объекта: 7861d080>)
  (330 . <Имя объекта: 7861d088>)
  (330 . <Имя объекта: 7861d090>)
  (330 . <Имя объекта: 7861d098>)
  (330 . <Имя объекта: 7861d0b8>)
  (330 . <Имя объекта: 7861d188>)
  (330 . <Имя объекта: 7861d1b0>)
  (330 . <Имя объекта: 7861d1b8>)
  (330 . <Имя объекта: 7861d1c0>)
  (330 . <Имя объекта: 7861d1c8>)
  (330 . <Имя объекта: 7861d1d0>)
  (330 . <Имя объекта: 7861d1d8>)
  (330 . <Имя объекта: 7861d1e0>)
  (330 . <Имя объекта: 7861d1e8>)
  (330 . <Имя объекта: 7861d1f0>)
  (330 . <Имя объекта: 7861d1f8>)
  (330 . <Имя объекта: 7861d200>)
  (330 . <Имя объекта: 7861d228>)
  (330 . <Имя объекта: 7861d230>)
  (330 . <Имя объекта: 7861d238>)
  (330 . <Имя объекта: 7861d240>)
  (330 . <Имя объекта: 78675a58>)
  (102 . "}")
  (330 . <Имя объекта: 78956c50>)
  (100 . "AcDbSymbolTableRecord")
  (100 . "AcDbDimStyleTableRecord")
  (2 . "SPDS$0")
  (70 . 0)
  (41 . 0.8)
  (42 . 1.0)
  (43 . 3.75)
  (44 . 0.75)
  (46 . 0.7)
  (49 . 1.25)
  (50 . 1.5708)
  (69 . 1)
  (73 . 0)
  (77 . 1)
  (78 . 1)
  (140 . 1.25)
  (141 . 1.25)
  (144 . 0.5)
  (146 . 0.75)
  (147 . 0.625)
  (172 . 1)
  (176 . 256)
  (177 . 256)
  (178 . 256)
  (271 . 1)
  (272 . 1)
  (278 . 44)
  (279 . 1)
  (284 . 8)
  (340 . <Имя объекта: 78907420>)
  (341 . <Имя объекта: 78907458>)
  (342 . <Имя объекта: 786a5530>)
  (371 . -1)
  (372 . -1)
)





_$ (assoc 330 (entget (vlax-vla-object->ename dst0)))
(330 . <Имя объекта: 78675a50>)
_$ (entget (cdr (assoc 330 (entget (vlax-vla-object->ename dst0)))))
((-1 . <Имя объекта: 78675a50>) (0 . "DIMENSION") (330 . <Имя объекта: 78675a20>) (5 . "63A") (100 . "AcDbEntity") (67 . 0) (8 . "ТС_вспом.") (62 . 2) (6 . "Continuous") (100 . "AcDbDimension") (2 . "*D82") (10 -158.825 164.581 0.0) (11 -163.341 170.595 0.0) (12 0.0 0.0 0.0) (70 . 0) (1 . "") (71 . 5) (72 . 1) (41 . 1.0) (42 . 7.0) (73 . 0) (74 . 0) (75 . 0) (52 . 0.0) (53 . 0.0) (54 . 0.0) (51 . 0.0) (210 0.0 0.0 1.0) (3 . "SPDS$0") (100 . "AcDbAlignedDimension") (13 -178.686 159.044 0.0) (14 -166.769 151.697 0.0) (15 0.0 0.0 0.0) (16 0.0 0.0 0.0) (40 . 0.0) (50 . 2.58912) (100 . "AcDbRotatedDimension"))
