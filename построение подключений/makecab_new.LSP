;;; изменена 10_08_11
;;; SignalList - глобальная переменная
;;; (("экран" <Entity name: 7edf8828>) ("экран" <Entity name: 7edf8700>) ("" <Entity name: 7edce2d0>) ("" <Entity name: 7edce228>) ("" <Entity name: 7edce140>) ("" <Entity name: 7edce098>) ("" <Entity name: 7edcdf88>) ("" <Entity name: 7edcdee0>) ("" <Entity name: 7edc7838>) ("" <Entity name: 7edc7770>) ("" <Entity name: 7edc76a8>) ("" <Entity name: 7edc74a8>) ("PE" <Entity name: 7edc3f80>) ("PE" <Entity name: 7edc3eb8>) ("PE" <Entity name: 7edc3df0>) ("PE" <Entity name: 7edc3ce8>) ("PE" <Entity name: 7edc3ba0>) ("PE" <Entity name: 7edc3a98>) ("PE" <Entity name: 7edc3990>) ("PE" <Entity name: 7edc38c8>) ("PE" <Entity name: 7edc3800>) ("PE" <Entity name: 7edc36f8>) ("PE" <Entity name: 7edc3630>) ("PE" <Entity name: 7edc3528>) ("PE" <Entity name: 7edc3420>) ("PE" <Entity name: 7edc32d8>) ("PE" <Entity name: 7edc31d0>) ("PE" <Entity name: 7edc3108>) ("2-N1" <Entity name: 7edb6920>) ("2-А62" <Entity name: 7edb6770>) ("3N208.5-2" <Entity name: 7edb6588>) ("3N208.5-3" <Entity name: 7edb6380>) ("[_[__]" <Entity name: 7edb61f8>) ("PE" <Entity name: 7edb5dd8>) ("[__]" <Entity name: 7edb5c08>) ("2-N1" <Entity name: 7edad020>) ("2-A62" <Entity name: 7edacf28>) ("3NT164-1" <Entity name: 7eda24f8>) ("3NT164-4" <Entity name: 7eda2408>) ("3NT164-5" <Entity name: 7eda2310>) ("3NT164-6" <Entity name: 7eda2258>) ("3NT163-1" <Entity name: 7eda1b90>) ("3NT163-4" <Entity name: 7eda1aa0>) ("3NT163-5" <Entity name: 7eda19e8>) ("3NT163-6" <Entity name: 7eda1970>) ("3NT162-1" <Entity name: 7eda12e8>) ("3NT162-4" <Entity name: 7eda11f8>) ("3NT162-5" <Entity name: 7eda1140>) ("3NT162-6" <Entity name: 7eda1088>) ("3NT161-1" <Entity name: 7eda0980>) ("3NT161-4" <Entity name: 7eda0890>) ("3NT161-5" <Entity name: 7eda0798>) ("3NT161-6" <Entity name: 7eda06e0>) ("3NT160-1" <Entity name: 7eda0098>) ("3NT160-4" <Entity name: 7ed9ef68>) ("3NT160-5" <Entity name: 7ed9eef0>) ("3NT160-6" <Entity name: 7ed9ee38>) ("3NT159-1" <Entity name: 7ed9e7b0>) ("3NT159-4" <Entity name: 7ed9e6c0>) ("3NT159-5" <Entity name: 7ed9e608>) ("3NT159-6" <Entity name: 7ed9e550>) ("3NT158-1" <Entity name: 7ed9dec8>) ("3NT158-4" <Entity name: 7ed9ddd8>) ("3NT158-5" <Entity name: 7ed9dd20>) ("3NT158-6" <Entity name: 7ed9dc68>) ("3NT157-1" <Entity name: 7ed9d5a0>) ("3NT157-4" <Entity name: 7ed9d4f0>) ("3NT157-5" <Entity name: 7ed9d438>) ("3NT157-6" <Entity name: 7ed9d340>) ("3NT156-1" <Entity name: 7ed9ccb8>) ("3NT156-4" <Entity name: 7ed9cb88>) ("3NT156-5" <Entity name: 7ed9cad0>) ("3NT156-6" <Entity name: 7ed9ca18>) ("3NT155-1" <Entity name: 7ed9c350>) ("3NT155-4" <Entity name: 7ed9c260>) ("3NT155-5" <Entity name: 7ed9c1a8>) ("3NT155-6" <Entity name: 7ed9c130>) ("3NT154-1" <Entity name: 7ed9baa8>) ("3NT154-4" <Entity name: 7ed9b9b8>) ("3NT154-5" <Entity name: 7ed9b900>) ("3NT154-6" <Entity name: 7ed9b848>) ("3NT153-1" <Entity name: 7ed9b140>) ("3NT153-4" <Entity name: 7ed9b050>) ("3NT153-5" <Entity name: 7ed9af58>) ("3NT153-6" <Entity name: 7ed9aea0>) ("3NT152-1" <Entity name: 7ed9a858>) ("3NT152-4" <Entity name: 7ed9a728>) ("3NT152-5" <Entity name: 7ed9a6b0>) ("3NT152-6" <Entity name: 7ed9a5f8>) ("3NT151-1" <Entity name: 7ed99f70>) ("3NT151-4" <Entity name: 7ed99e80>) ("3NT151-5" <Entity name: 7ed99dc8>) ("3NT151-6" <Entity name: 7ed99d10>) ("3NT150-1" <Entity name: 7ed99688>) ("3NT150-4" <Entity name: 7ed99598>) ("3NT150-5" <Entity name: 7ed994e0>) ("3NT150-6" <Entity name: 7ed99428>) ("3NT149-1" <Entity name: 7ed989d0>) ("3NT149-4" <Entity name: 7ed98928>) ("3NT149-5" <Entity name: 7ed98868>) ("3NT149-6" <Entity name: 7ed98770>) ("3NF296-1" <Entity name: 7ed6f8b8>) ("3NF295-1" <Entity name: 7ed6f820>) ("peзepв-1" <Entity name: 7ed6f748>) ("peзepв-1" <Entity name: 7ed6f6f0>) ("PE" <Entity name: 7ed6f680>) ("1-A62" <Entity name: 7ed6f610>) ("1-N1" <Entity name: 7ed6f558>) ("peзepв-2" <Entity name: 7ed6ee80>) ("peзepв-3" <Entity name: 7ed6edc8>) ("peзepв-2" <Entity name: 7ed6ed10>) ("peзepв-3" <Entity name: 7ed6ec58>) ("3NF296-2" <Entity name: 7ed6eb60>) ("3NF296-3" <Entity name: 7ed6eaa8>) ("3NF295-2" <Entity name: 7ed6ea30>) ("3NF295-3" <Entity name: 7ed6e978>) ("3NP275-1" <Entity name: 7ed6e630>) ("3NP274-1" <Entity name: 7ed6e598>) ("3NP276-1" <Entity name: 7ed6e500>) ("3NP277-1" <Entity name: 7ed6e468>) ("PE" <Entity name: 7ed6e3b8>) ("1-A62" <Entity name: 7ed6e348>) ("1-N1" <Entity name: 7ed6e290>) ("3NP277-2" <Entity name: 7ed6dbb8>) ("3NP277-3" <Entity name: 7ed6db00>) ("3NP276-2" <Entity name: 7ed6da48>) ("3NP276-3" <Entity name: 7ed6d990>) ("3NP275-2" <Entity name: 7ed6d8d8>) ("3NP275-3" <Entity name: 7ed6d820>) ("3NP274-2" <Entity name: 7ed6d728>) ("3NP274-3" <Entity name: 7ed6d6b0>) ("3NP251-1" <Entity name: 7ed6d328>) ("3NP250-1" <Entity name: 7ed6d290>) ("3NP268-1" <Entity name: 7ed6d1f8>) ("3NP269-1" <Entity name: 7ed6d160>) ("PE" <Entity name: 7ed6d0f0>) ("1-A62" <Entity name: 7ed6d080>) ("1-N1" <Entity name: 7ed6cf88>) ("3NP269-2" <Entity name: 7ed6c8f0>) ("3NP269-3" <Entity name: 7ed6c838>) ("3NP268-2" <Entity name: 7ed6c740>) ("3NP268-3" <Entity name: 7ed6c688>) ("3NP251-2" <Entity name: 7ed6c5d0>) ("3NP251-3" <Entity name: 7ed6c518>) ("3NP250-2" <Entity name: 7ed6c460>) ("3NP250-3" <Entity name: 7ed6c368>) ("PE" <Entity name: 7ed6af68>) ("1-A62" <Entity name: 7ed6aef8>) ("1-N1" <Entity name: 7ed6ae40>) ("3NT164-3" <Entity name: 7ed6a6f0>) ("3NT163-3" <Entity name: 7ed6a600>) ("3NT162-3" <Entity name: 7ed6a510>) ("3NT161-3" <Entity name: 7ed6a420>) ("3NF294-1" <Entity name: 7ed6a050>) ("3NF293-1" <Entity name: 7ed69f78>) ("peзepв-1" <Entity name: 7ed69ee0>) ("peзepв-1" <Entity name: 7ed69e48>) ("PE" <Entity name: 7ed69dd8>) ("1-A62" <Entity name: 7ed69d68>) ("1-N1" <Entity name: 7ed69cf0>) ("peзepв-2" <Entity name: 7ed69558>) ("peзepв-3" <Entity name: 7ed694a0>) ("peзepв-2" <Entity name: 7ed693a8>) ("peзepв-3" <Entity name: 7ed69330>) ("3NF294-2" <Entity name: 7ed69278>) ("3NF294-3" <Entity name: 7ed691c0>) ("3NF293-2" <Entity name: 7ed69108>) ("3NF293-3" <Entity name: 7ed69050>) ("3NP273-1" <Entity name: 7ed68d08>) ("3NP272-1" <Entity name: 7ed68cb0>) ("peзepв-1" <Entity name: 7ed68c18>) ("peзepв-1" <Entity name: 7ed68b40>) ("PE" <Entity name: 7ed68ad0>) ("1-A62" <Entity name: 7ed68a60>) ("1-N1" <Entity name: 7ed689a8>) ("peзepв-2" <Entity name: 7ed68250>) ("peзepв-3" <Entity name: 7ed68198>) ("peзepв-2" <Entity name: 7ed680e0>) ("peзepв-3" <Entity name: 7ed68028>) ("3NP273-2" <Entity name: 7ed67f70>) ("3NP273-3" <Entity name: 7ed67eb8>) ("3NP272-2" <Entity name: 7ed67e00>) ("3NP272-3" <Entity name: 7ed67d48>) ("3NP247-1" <Entity name: 7ed679c0>) ("3NP246-1" <Entity name: 7ed67928>) ("3NP248-1" <Entity name: 7ed67890>) ("3NP249-1" <Entity name: 7ed677b8>) ("PE" <Entity name: 7ed67748>) ("1-A62" <Entity name: 7ed676d8>) ("1-N1" <Entity name: 7ed67620>) ("3NP249-2" <Entity name: 7ed66f08>) ("3NP249-3" <Entity name: 7ed66e50>) ("3NP248-2" <Entity name: 7ed66d98>) ("3NP248-3" <Entity name: 7ed66ce0>) ("3NP247-2" <Entity name: 7ed66c28>) ("3NP247-3" <Entity name: 7ed66b70>) ("3NP246-2" <Entity name: 7ed66ab8>) ("3NP246-3" <Entity name: 7ed66a00>) ("PE" <Entity name: 7ed666c0>) ("1-A62" <Entity name: 7ed66650>) ("1-N1" <Entity name: 7ed66598>) ("3NT160-3" <Entity name: 7ed65e88>) ("3NT159-3" <Entity name: 7ed65d98>) ("3NT158-3" <Entity name: 7ed65ca8>) ("3NT157-3" <Entity name: 7ed65b78>) ("3NF219.4-1" <Entity name: 7ed65870>) ("3NF218.4-1" <Entity name: 7ed65798>) ("peзepв-1" <Entity name: 7ed65700>) ("peзepв-1" <Entity name: 7ed65668>) ("PE" <Entity name: 7ed655f8>) ("2-A62" <Entity name: 7ed65588>) ("2-N1" <Entity name: 7ed654d0>) ("peзepв-2" <Entity name: 7ed64df8>) ("peзepв-3" <Entity name: 7ed64d40>) ("peзepв-2" <Entity name: 7ed64c88>) ("peзepв-3" <Entity name: 7ed64b90>) ("3NF219.4-2" <Entity name: 7ed64ad8>) ("3NF219.4-3" <Entity name: 7ed64a20>) ("3NF218.4-2" <Entity name: 7ed64968>) ("3NF218.4-3" <Entity name: 7ed648f0>) ("3NF201.5-1" <Entity name: 7ed64568>) ("3NF201.4-1" <Entity name: 7ed644d0>) ("peзepв-1" <Entity name: 7ed64438>) ("peзepв-1" <Entity name: 7ed64360>) ("PE" <Entity name: 7ed642f0>) ("2-A62" <Entity name: 7ed64280>) ("2-N1" <Entity name: 7ed641c8>) ("peзepв-2" <Entity name: 7ed63af0>) ("peзepв-3" <Entity name: 7ed63a38>) ("peзepв-2" <Entity name: 7ed63980>) ("peзepв-3" <Entity name: 7ed638c8>) ("3NF201.5-2" <Entity name: 7ed63810>) ("3NF201.5-3" <Entity name: 7ed63718>) ("3NF201.4-2" <Entity name: 7ed63660>) ("3NF201.4-3" <Entity name: 7ed635a8>) ("3NP271-1" <Entity name: 7ed631e0>) ("3NP270-1" <Entity name: 7ed63148>) ("peзepв-1" <Entity name: 7ed630f0>) ("peзepв-1" <Entity name: 7ed63058>) ("PE" <Entity name: 7ed62fa8>) ("1-A62" <Entity name: 7ed62f38>) ("1-N1" <Entity name: 7ed62e80>) ("peзepв-2" <Entity name: 7ed62728>) ("peзepв-3" <Entity name: 7ed626b0>) ("peзepв-2" <Entity name: 7ed625f8>) ("peзepв-3" <Entity name: 7ed62540>) ("3NP271-2" <Entity name: 7ed62488>) ("3NP271-3" <Entity name: 7ed62390>) ("3NP270-2" <Entity name: 7ed622d8>) ("3NP270-3" <Entity name: 7ed62220>) ("3NP175-1" <Entity name: 7ed61e98>) ("3NP169-1" <Entity name: 7ed61e00>) ("3NP176-1" <Entity name: 7ed61d68>) ("peзepв-1" <Entity name: 7ed61cd0>) ("PE" <Entity name: 7ed61c60>) ("1-A62" <Entity name: 7ed61bb0>) ("1-N1" <Entity name: 7ed61af8>) ("peзepв-2" <Entity name: 7ed61360>) ("peзepв-3" <Entity name: 7ed612a8>) ("3NP176-2" <Entity name: 7ed61230>) ("3NP176-3" <Entity name: 7ed61178>) ("3NP175-2" <Entity name: 7ed610c0>) ("3NP175-3" <Entity name: 7ed61008>) ("3NP169-2" <Entity name: 7ed5ff10>) ("3NP169-3" <Entity name: 7ed5fe58>) ("PE" <Entity name: 7ed5fa98>) ("1-A62" <Entity name: 7ed5fa28>) ("1-N1" <Entity name: 7ed5f9b0>) ("3NT156-3" <Entity name: 7ed5f1e0>) ("3NT155-3" <Entity name: 7ed5f130>) ("3NT154-3" <Entity name: 7ed5f040>) ("3NT153-3" <Entity name: 7ed5ef10>) ("3NF217.4-1" <Entity name: 7ed5ec08>) ("3NF216.4-1" <Entity name: 7ed5eb70>) ("3NF236.6-1" <Entity name: 7ed5ead8>) ("peзepв-1" <Entity name: 7ed5ea40>) ("PE" <Entity name: 7ed5e9d0>) ("2-A62" <Entity name: 7ed5e960>) ("2-N1" <Entity name: 7ed5e8a8>) ("peзepв-2" <Entity name: 7ed5e150>) ("peзepв-3" <Entity name: 7ed5e098>) ("3NF236.6-2" <Entity name: 7ed5cfa0>) ("3NF236.6-3" <Entity name: 7ed5cee8>) ("3NF217.4-2" <Entity name: 7ed5ce70>) ("3NF217.4-3" <Entity name: 7ed5cdb8>) ("3NF216.4-2" <Entity name: 7ed5cd00>) ("3NF216.4-3" <Entity name: 7ed5cc48>) ("3NF281-1" <Entity name: 7ed5c8c0>) ("3NF280-1" <Entity name: 7ed5c828>) ("peзepв-1" <Entity name: 7ed5c750>) ("peзepв-1" <Entity name: 7ed5c6b8>) ("PE" <Entity name: 7ed5c648>) ("1-A62" <Entity name: 7ed5c5d8>) ("1-N1" <Entity name: 7ed5c520>) ("peзepв-2" <Entity name: 7ed5be08>) ("peзepв-3" <Entity name: 7ed5bd50>) ("peзepв-2" <Entity name: 7ed5bc98>) ("peзepв-3" <Entity name: 7ed5bba0>) ("3NF281-2" <Entity name: 7ed5bae8>) ("3NF281-3" <Entity name: 7ed5ba70>) ("3NF280-2" <Entity name: 7ed5b9b8>) ("3NF280-3" <Entity name: 7ed5b900>) ("3NP265-1" <Entity name: 7ed5b5b8>) ("3NP264-1" <Entity name: 7ed5b520>) ("peзepв-1" <Entity name: 7ed5b488>) ("peзepв-1" <Entity name: 7ed5b430>) ("PE" <Entity name: 7ed5b380>) ("1-A62" <Entity name: 7ed5b310>) ("1-N1" <Entity name: 7ed5b258>) ("peзepв-2" <Entity name: 7ed5ab80>) ("peзepв-3" <Entity name: 7ed5aac8>) ("peзepв-2" <Entity name: 7ed5aa10>) ("peзepв-3" <Entity name: 7ed5a958>) ("3NP265-2" <Entity name: 7ed5a8a0>) ("3NP265-3" <Entity name: 7ed5a7a8>) ("3NP264-2" <Entity name: 7ed5a730>) ("3NP264-3" <Entity name: 7ed5a678>) ("3NP205-1" <Entity name: 7ed5a330>) ("3NP181-1" <Entity name: 7ed5a298>) ("peзepв-1" <Entity name: 7ed5a200>) ("peзepв-1" <Entity name: 7ed5a168>) ("PE" <Entity name: 7ed5a0f8>) ("1-A62" <Entity name: 7ed5a088>) ("1-N1" <Entity name: 7ed59f90>) ("peзepв-2" <Entity name: 7ed598f8>) ("peзepв-3" <Entity name: 7ed59840>) ("peзepв-2" <Entity name: 7ed59748>) ("peзepв-3" <Entity name: 7ed59690>) ("3NP205-2" <Entity name: 7ed595d8>) ("3NP205-3" <Entity name: 7ed59520>) ("3NP181-2" <Entity name: 7ed59468>) ("3NP181-3" <Entity name: 7ed593b0>) ("PE" <Entity name: 7ed59070>) ("1-A62" <Entity name: 7ed59000>) ("1-N1" <Entity name: 7ed58f08>) ("3NT152-3" <Entity name: 7ed587b8>) ("3NT151-3" <Entity name: 7ed586c8>) ("3NT150-3" <Entity name: 7ed585d8>) ("3NT149-3" <Entity name: 7ed584e8>) ("PE" <Entity name: 7ed57ee8>) ("2-A62" <Entity name: 7ed57e78>) ("2-N1" <Entity name: 7ed57dc0>) ("PE" <Entity name: 7ed56b60>) ("2-A62" <Entity name: 7ed56af0>) ("2-N1" <Entity name: 7ed56a38>) ("PE" <Entity name: 7ed49b50>) ("2-A62" <Entity name: 7ed49ae0>) ("2-N1" <Entity name: 7ed49a28>) ("PE" <Entity name: 7ed44f70>) ("2-A62" <Entity name: 7ed44f00>) ("2-N1" <Entity name: 7ed44e48>))
;;; запуск программы с коммандной строки :
;;; (getclamps)
;;; (makecab)
;;; getclamps создает базу проекта вида списка ((<марка связи> <имя блока клеммки>) ...)
;;; принимает набор ряда зажимов (фильтрует по слою "клеммы")
;;; из этого набора потом будут выбираться блоки "клеммы" при подключении кабеля
;;; makecab - указывается (например из чертежей трасс) марки сигналов одного кабеля
;;; они подсвечиваются зеоеным и на рядах зажимов появляются "выводы жил данного кабеля"
;;; -kakt00z-™  ©

(defun getclamps (
	    /
	    doc
	    ss
	    ;SignalList
	    tmpbname
	    tmpattname
	    attstr
	    i
	    )
  ;(load "D:\\LISP WORKING\\Блоки Аттрибуты Тексты\\getbatt.LSP")

  (setq doc (vla-get-activedocument (vlax-get-acad-object)))
  (vla-startundomark doc)
  (acet-error-init
    (list (list "cmdecho" 0
               "expert" nil
        );list
        T
  );list
 );acet-error-init
  

  
  (setq ss (ssget '((0 . "INSERT")(8 . "клеммы")))
	i 0
	SignalList '())
  
  (repeat (sslength ss)
    (setq tmpbname (ssname ss i)
	  SignalList (append SignalList (list
					  (list
					    ;(cdr (assoc 1 (entget (getbatt* tmpbname "МАРКА_СВЯЗИ"))))
					    (cdr (assoc 1 (entget
							    (vlax-vla-object->ename
							      (getbatt (vlax-ename->vla-object tmpbname) "MARK")
							      )
							    )))
					    tmpbname
					  )
					  ))
	  i (1+ i))
    );repeat
  
  ;(sssetfirst nil ss)
  Signallist
  

  (acet-error-restore)
  (vla-endundomark doc)
  );defun


(defun c:mc ()(makecab))

(defun makecab (
		/
		doc
		ss
		i
		;sl
		cblc	;current block connecting
		tmp
		errmess

		c
		entg
		ent
		)
  (setq doc (vla-get-activedocument (vlax-get-acad-object)))
  (vla-startundomark doc)
  (acet-error-init
    (list (list "cmdecho" 0
               "expert" nil
        );list
        T
  );list
 );acet-error-init
  
  (setq ss (ssget '((0 . "*TEXT")))
	i 0
	sl '()
	tmp nil
	errmess "")



;;;  (repeat (sslength ss)
;;;    (setq sl (append sl (list (cdr (assoc 1 (entget (ssname ss i))))))
;;;	  i (1+ i))
;;;    )

  (setq ss (ss->list* ss))


  (foreach item ss
    (if (setq tmp (assoc (cdr (assoc 1 (entget item))) SignalList))
      ;если есть ******************************************************
      (progn
	(drawzhila (cadr tmp) 2.5)
	(setq ent item
	      c	(assoc 62 (entget ent))
	      entg	(entget ent)
	      )
	(if (not c)
	  (setq entg (append entg '((62 . 3))))
	  (setq entg (subst '(62 . 3) (assoc 62 entg) entg))
	  );if not c
	(entmod entg)
	(entupd ent)
	);progn
      ;if no ******************************************************
      (progn
	(setq errmess (strcat errmess " " (cdr (assoc 1 (entget item))) "\n"))
	(setq ent item
	      c	(assoc 62 (entget ent))
	      entg	(entget ent)
	      )
	(if (not c)
	  (setq entg (append entg '((62 . 1))))
	  (setq entg (subst '(62 . 1) (assoc 62 entg) entg))
	  );if not c
	(entmod entg)
	(entupd ent)
	
      )
      );if
    );foreach
  (if (/= "" errmess)
    (princ (strcat " *******   не найдены ******  \n" errmess))
    )
  (acet-error-restore)
  (vla-endundomark doc)
  )






(defun drawzhila (bl y+
		  /
		  sal
		  mirrored
		  
		  ptb
		  pt10
		  pt11
		  step
		  )

  (setq step 6)



  
  (setq sal (vlax-safearray->list
		   (vlax-variant-value
		     (vla-getDynamicBlockProperties
		       (vlax-ename->vla-object bl)))))
  (foreach item sal
    (if (= (vla-get-PropertyName item) "Отраженное состояние")
      (setq mirrored (vlax-variant-value (vla-get-Value item)))
      );if
    )
  (if (null mirrored)
    (progn
      (alert "не найден дин. параметр блока блока")
      (setq mirrored T)
      )
    )

  (setq ptb (cdr (assoc 10 (entget bl))))
  (if (= mirrored 1)
    (setq pt10 (list (- (car ptb) 40) (+ (cadr ptb) y+))
	  pt11 (list (- (car ptb) (+ 40 (* step 3))) (+ (cadr ptb) y+))
	  )
    (setq pt10 (list (+ (car ptb) 40) (+ (cadr ptb) y+) )
	  pt11 (list (+ (car ptb) (+ 40 (* step 3))) (+ (cadr ptb) y+) )
	  )
    
    );if

  (entmakex (append '((0 . "LINE")
		      (62 . 3)
		      ;(370 . 60)
		      (8 . "0"))
		    (list
		      (cons 10 pt10)
		      (cons 11 pt11)
		      )
		    )
	    );etmakex
  );defun
