;; первращение линии в кабель с данными

(setq od (namedobjdict))

(dictadd od
	 "cable-data"
	 (entmakex '((0 . "DICTIONARY")(100 . "AcDbDictionary")))
	 );dictadd

(setq crec '((0 . "XRECORD") ;; (100 . "AcDbXrecord")
	     (300 . "наименование единицы")
	     (301 . "cable")
	     (300 . "номер")
	     (301 . "5М_1699")
	     (300 . "тип")
	     (301 . "КВВГЭ")
	     (300 . "наличие экрана")
	     (301 . 1)
	     (300 . "жильность")
	     (301 . 7)
	     (300 . "толщина сечения жилы")
	     (301 . 1.5)
	     (300 . "место источника сигнала (откуда)")
	     (301 . "Коробка соединительнвя")
	     (300 . "маркировка места источника сигнала")
	     (301 . "5Г-СК6")
	     (300 . "место приемника сигнала (куда)")
	     (301 . "Местный щиток №1")
	     (300 . "маркировка места приемника сигнала")
	     (301 . "X1")
	     (300 . "передаваемые сигналы")
	     (301 . "5М_ТС001")
	     (302 . "5М_ТС002")
	     (300 . "передаваемые жилы")
	     (301 . "5М_ТС001.1-1")
	     (302 . "5М_ТС001.1-2")
	     (303 . "5М_ТС002.1-1")
	     (304 . "5М_ТС002.1-2")
	     (399 . "Экран")
	     ))

(setq ecrec (entmakex crec))
