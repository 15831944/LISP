;;;; cab - ñïèñîê (("3N-641" "3NÒ150-6" "3NÒ150-5" "3NÒ150-4" "3NÒ149-6" "3NÒ149-5" "3NÒ149-4") ("3N-642" "3NÒ152-6" "3NÒ152-5" "3NÒ152-4" "3NÒ151-6" "3NÒ151-5" "3NÒ151-4") ("3N-643" "3NÒ158-6" "3NÒ157-6" "3NÒ156-6" "3NÒ155-6" "3NÒ154-6" "3NÒ153-6" "3NÒ158-5" "3NÒ158-4" "3NÒ157-5" "3NÒ157-4" "3NÒ156-5" "3NÒ156-4" "3NÒ155-5" "3NÒ155-4" "3NÒ154-5" "3NÒ154-4" "3NÒ153-5" "3NÒ153-4") ("3N-644" "3NÒ164-6" "3NÒ164-5" "3NÒ164-4" "3NÒ163-6" "3NÒ163-5" "3NÒ163-4" "3NÒ162-6" "3NÒ162-5" "3NÒ162-4" "3NÒ161-6" "3NÒ161-5" "3NÒ161-4" "3NÒ160-6" "3NÒ160-5" "3NÒ160-4" "3NÒ159-6" "3NÒ159-5" "3NÒ159-4"))
;;; óêàçûâàåì íîìåð êàáåëÿ - çàòåì ìàðêè æèëîê â íåì
(defun associng (
		 /
		 obj
		 ss
		 lst
		 )
  (while (setq obj (entsel "\nSelect assoc object..."))
    (setq obj (vlax-ename->vla-object (car obj)))
    (setq ss (mapcar 'vlax-ename->vla-object (ss->list* (ssget '((0 . "*TEXT"))))))
    (setq lst (append lst (list (append (list obj) ss))))
    )
  lst
  );defun


(defun map (func arg lst)
  (mapcar
    '(lambda (x)
       (mapcar
	 '(lambda (y)
	    (if arg
	      (func y arg)
	      (func y)
	      )
	    )
	 x
	 )
       )
    lst
    )
  );defun

(setq cab (map vla-get-TextString  nil (associng)))



;;;; â ñîîòâåòñòâèè


(defun qwer (lst
	     /
	     )
  
  );defun 


(setq c1 (nth 0 cab))
(setq number (car c1)
      marks (cdr c1))

(setq clamp (mapcar 'vlax-ename->vla-object (ss->list*(ssget '((0 . "INSERT")(8 . "êëåììû"))))))

(foreach cl clamp
  (setq mark (vla-get-TextString (getbatt cl "MARK")))
  (if (member mark marks)
    (connectwireto cl)
    )
  )


(defun connectwireto (obj
		      /\
		      )
  
  );defun
