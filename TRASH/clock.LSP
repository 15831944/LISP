;;;==============================================================
;;;=========== deg2rad ==========================================
;;;==============================================================
(defun deg2rad (deg)
  (* deg (/ pi 180))
)
;;;==============================================================
;;;==============================================================

;;;==============================================================
;;;=========== do_end ===========================================
;;;==============================================================
(defun do_end (l fi)
;;; вводим длину и угол в град.
  (list	(* l (cos (deg2rad fi)))
;;; X
	(* l (sin (deg2rad fi)))
;;; Y
  )
)
;;; возвращает список с координатами конца отрезка
;;;==============================================================
;;;==============================================================







(defun c:clock (/ radius engl_deg engl_radian b_pt end_pt i)
  (setq	radius 100
	b_pt '(0 0)
	i 90
	enle_deg 0
  )

;;; внешний круг часов  
  (command "_.circle" b_pt (+ radius 20))



  (while (< i 180)
    (progn
      (setq end_pt (do_end radius i))
      (command "_.line" b_pt end_pt "")
      (princ end_pt)
      (command "_.erase" (entlast) "" )
      (princ)
      (setq i (1- i))
    );progn
  ) ;while

);defun
