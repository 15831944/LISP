;;; прога делает из ssget (разбитых) листов спецификации
;;; список по строкам
;;; ((A1 B1 C1 ...) (A2 B2 C2 ...) ...)

;;;  спецификация должна быть
;;; 1 выполнена в ворматах А3 по госту БелНИПИ с маленькими штампами
;;; 2 первый лист с большим штампом заменить на маленький штамп, удалить примечания
;;; 3 графа "Кол. уч." д.б. шрифтом 2.5 если масштаб 1:1
;;; 4 высота строки - 8 мм (в масштабе 1:1), 27 или менее строк
;;; 5 без мультитекстов
;;; 6 разбита, без полилиний, и прогнана через прогу express "delete duplicate objects"

(load "d:/_LISP/common functions/format-identification-gost.lsp")



(vl-load-com)
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
(defun spec2table (
		  /
		  doc
		  lstkoluch
		  formatlist
		  datalst
		  
		  dwgscale	;масштаб документа
		  ColWidthLst	;список нирин столбцов
		  LineHeight	;высота строки
		  NumberOfLines
		  getlist getrow mergetxt
		  )
;;;-------------------------------------------------------------
;;; constants  
;;;-------------------------------------------------------------

  (setq dwgscale 1

	;(tbl>lst)


	
	;spec
	;colwidthlst '(20 130 60 35 45 20 20 25 40)

	

	;  перечень электрифицированной арматуры т теплотехников
	;   проставляем размеры, взрываем их и
	;(tbl>lst)
	;colwidthlst (mapcar 'read '("23" "69" "13" "22" "31" "36" "34" "22" "28" "28" "28" "28" "33"))
	;lineheight 8

	
	;переч
	;colwidthlst '(30 130 25 25 25 105 25 30)
	;lineheight 8
	;NumberOfLines 27

	; КЖ
	colwidthlst '(90 25 55 55 35 15 20 14 85)
	TblHeadHeight 15
	lineheight 12
	NumberOfLines 20


	)
;;;-------------------------------------------------------------
;;;-------------------------------------------------------------
;;;-------------------------------------------------------------


  


;;;************************************************************
;;;           getlist
;;;************************************************************
;(setq drwlst (car formatlist))

(defun getlist (drwlst / lst ptmp)
  (vl-cmdf "_.zoom" (cadr drwlst) (caddr drwlst))
  (setq ptmp (mapcar '+ (cadr drwlst) (mapcarx * dwgscale (list 20 (- 292 TblHeadHeight)))) lst '())
  
  (repeat NumberOfLines
    (setq lst (append lst (list (getrow ptmp)))
	  ptmp (polar ptmp (/ Pi -2) (* LineHeight dwgscale)))
    );repeat
  lst
  );defun
;(getlist drwlst)




;;;************************************************************
;;;           getrow
;;;************************************************************

;(setq rowpoint (getpoint))
;(getrow (getpoint))
;(setq colwidthlst '(20 205) NumberOfLines 27)

(defun getrow (rowpoint / ss lst cellconer i)
  ;(setq tmp p0)
  (setq lst '() i -1 cellconer (mapcar '+ rowpoint (mapcarx * dwgscale '(1 -1))))
  (repeat (length colwidthlst)
    (setq i (1+ i))
    (setq ss (ssget "_C" cellconer (mapcar '+ cellconer (list (- (nth i colwidthlst) (* 2 dwgscale)) (* (- (- lineheight 2)) dwgscale))) '((0 . "TEXT"))))
    (cond
      ((null ss)		(setq lst (append lst (list nil))))
      ((= (sslength ss) 1)	(setq lst (append lst (list (cdr (assoc 1 (entget (ssname ss 0))))))))
      ((> (sslength ss) 1)	(setq lst (append lst (list (mergetxt ss)))))
      );cond
    (setq cellconer (mapcar '+ cellconer (list (nth i colwidthlst) 0)))
    );repeat
  lst
  );defun
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;(setq ss (ssget))
  ;(mergetxt ss)
  (defun mergetxt ( ss / ssl textheight)
    (setq ssl (ss->list* ss))
    (setq textheight (ziplist (mapcar '(lambda (e) (list (cdr (assoc 40 (entget e))) 1)) ssl)))
    (setq textheight (mapcar '(lambda (x) (cons (apply '+ (cdr x)) (car x))) textheight))
    (setq textheight (cdr (assoc (eval (cons 'max (mapcar 'car textheight))) textheight)))
    (setq ssl (vl-sort ssl '(lambda (a b) (> (car (cdr (assoc 10 (entget b)))) (car (cdr (assoc 10 (entget a))))))))
    (setq ssl (vl-sort ssl '(lambda (a b) (> (- (cadr (cdr (assoc 10 (entget a)))) (cadr (cdr (assoc 10 (entget b))))) textheight))))
    (antisep (mapcar '(lambda (e) (cdr (assoc 1 (entget e)))) ssl) " ")
    );defun





  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  (vla-startundomark #actdoc)
  (acet-error-init (list (list "cmdecho" 0 "highlight" (getvar "highlight") "limcheck" 0 "osmode" 0 ) T))



  
  (setq lstkoluch (get-kol-uch))
  ;;; формируем список вида (n (x1 y1)(x2 y2))
  ;;; где n - номер листа,
  ;;; (...)(...) - координаты углов листа - левый нижний
  (setq formatlist (mapcar '(lambda (x) (cons (FG|getsheetnumber (vlax-ename->vla-object x)) (get-formatpts<-rightformatline (get-rightformatline<-koluch x)))) lstkoluch))
  ;;;*********************************************
  ;;; сортируем по номеру листа			 *
  ;;;*********************************************
  (setq	formatlist (vl-sort formatlist '(lambda (a b) (< (car a) (car b)))))
  ;;;*********************************************


  ;;;*********************************************
  ;;; формируем список для передачи в ексель     *
  ;;;*********************************************
  (setq datalst '())
  (foreach item formatlist
    (setq datalst (append datalst (getlist item)))
    );foreach
  ;;;*********************************************

  
  ;;;-------------------------------------------------------------
  (acet-error-restore)
  (vla-endundomark #actdoc)
  ;(vl-cmdf "_.zoom" "_a")
  datalst
  );defun
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




;; !!!    взорвать мультитексты !!!!

(setq scale 1)
(setq lst (spec2table))
(length lst)


(nth 13 lst)


(lst>excel lst)







;(setq tst (vl-remove-if-not '(lambda (line) (apply 'or line)) lst))
;(lst>excel lst)











;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;
(defun spec2data (
		  /
		
		  drws
		  formatlist
		  datalst
		  
		  dwgscale	;масштаб документа
		  ColWidthLst	;список нирин столбцов
		  LineHeight	;высота строки
		  NumberOfLines
		  getlist getrow mergetxt
		  )
;;;-------------------------------------------------------------
;;; constants  
;;;-------------------------------------------------------------

  (setq dwgscale 1

	;  перечень электрифицированной арматуры т теплотехников
	;   проставляем размеры, взрываем их и
	;(tbl>lst)
	;colwidthlst (mapcar 'read '("23" "69" "13" "22" "31" "36" "34" "22" "28" "28" "28" "28" "33"))
	;lineheight 8
	;TblHeadHeight 50
	;NumberOfLines 25

	;	CUSTOM

	colwidthlst (mapcar 'read '("23" "226" "43" "13" "22" "31" "36" "34" "22" "28" "28" "28" "28"))
	lineheight 8
	TblHeadHeight 50
	NumberOfLines 25

	
	;переч
	;colwidthlst '(30 130 25 25 25 105 25 30)
	;lineheight 8
	;NumberOfLines 27

	; КЖ
	;colwidthlst '(90 25 55 55 35 15 20 14 85)
	;TblHeadHeight 15
	;lineheight 12
	;NumberOfLines 20


	)
;;;-------------------------------------------------------------
;;;-------------------------------------------------------------
;;;-------------------------------------------------------------


  


;;;************************************************************
;;;           getlist
;;;************************************************************
;(setq drwlst (car formatlist))

;  (vla-AddCircle #modspace (vlax-3d-point ptmp) 10)

  
(defun getlist (drwlst / lst ptmp)
  (vl-cmdf "_.zoom" (cadr drwlst) (caddr drwlst))
  (setq ptmp (mapcar '+ (cadr drwlst)
		     (mapcarx * dwgscale (list 20 (- 292 TblHeadHeight)))
		     ) lst '())
  
  (repeat NumberOfLines
    (setq lst (append lst (list (getrow ptmp)))
	  ptmp (polar ptmp (/ Pi -2) (* LineHeight dwgscale)))
    );repeat
  lst
  );defun
;(getlist drwlst)




;;;************************************************************
;;;           getrow
;;;************************************************************

;(setq rowpoint (getpoint))
;(getrow (getpoint))
;(setq colwidthlst '(20 205) NumberOfLines 27)

(defun getrow (rowpoint / ss lst cellconer i)
  ;(setq tmp p0)
  (setq lst '() i -1 cellconer (mapcar '+ rowpoint (mapcarx * dwgscale '(1 -1))))
  (repeat (length colwidthlst)
    (setq i (1+ i))
    (setq ss (ssget "_C" cellconer (mapcar '+ cellconer (list (- (nth i colwidthlst) (* 2 dwgscale)) (* (- (- lineheight 2)) dwgscale))) '((0 . "TEXT"))))
    (cond
      ((null ss)		(setq lst (append lst (list nil))))
      ((= (sslength ss) 1)	(setq lst (append lst (list (cdr (assoc 1 (entget (ssname ss 0))))))))
      ((> (sslength ss) 1)	(setq lst (append lst (list (mergetxt ss)))))
      );cond
    (setq cellconer (mapcar '+ cellconer (list (nth i colwidthlst) 0)))
    );repeat
  lst
  );defun
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;(setq ss (ssget))
  ;(mergetxt ss)
  (defun mergetxt ( ss / ssl textheight)
    (setq ssl (ss->list* ss))
    (setq textheight (ziplist (mapcar '(lambda (e) (list (cdr (assoc 40 (entget e))) 1)) ssl)))
    (setq textheight (mapcar '(lambda (x) (cons (apply '+ (cdr x)) (car x))) textheight))
    (setq textheight (cdr (assoc (eval (cons 'max (mapcar 'car textheight))) textheight)))
    (setq ssl (vl-sort ssl '(lambda (a b) (> (car (cdr (assoc 10 (entget b)))) (car (cdr (assoc 10 (entget a))))))))
    (setq ssl (vl-sort ssl '(lambda (a b) (> (- (cadr (cdr (assoc 10 (entget a)))) (cadr (cdr (assoc 10 (entget b))))) textheight))))
    (antisep (mapcar '(lambda (e) (cdr (assoc 1 (entget e)))) ssl) " ")
    );defun





  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  (vla-startundomark #actdoc)
  (acet-error-init (list (list "cmdecho" 0 "highlight" (getvar "highlight") "limcheck" 0 "osmode" 0 ) T))



  
  (setq lstkoluch (get-kol-uch))
  ;;; формируем список вида (n (x1 y1)(x2 y2))
  ;;; где n - номер листа,
  ;;; (...)(...) - координаты углов листа - левый нижний
  (setq formatlist (mapcar '(lambda (x) (cons (FG|getsheetnumber (vlax-ename->vla-object x)) (get-formatpts<-rightformatline (get-rightformatline<-koluch x)))) lstkoluch))
  ;;;*********************************************
  ;;; сортируем по номеру листа			 *
  ;;;*********************************************
  (setq	formatlist (vl-sort formatlist '(lambda (a b) (< (car a) (car b)))))
  ;;;*********************************************


  ;;;*********************************************
  ;;; формируем список для передачи в ексель     *
  ;;;*********************************************
  (setq datalst '())
  (foreach item formatlist
    (setq datalst (append datalst (getlist item)))
    );foreach
  ;;;*********************************************

  
  ;;;-------------------------------------------------------------
  (acet-error-restore)
  (vla-endundomark #actdoc)
  ;(vl-cmdf "_.zoom" "_a")
  datalst
  );defun
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;








;; !!!    взорвать мультитексты !!!!

(setq scale 1)
(setq lst (spec2data))
(length lst)
(lst>excel lst)
