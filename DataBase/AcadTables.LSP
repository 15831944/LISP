(defun AcadTbl|getcontent (obj / rows cols val i j res line)
  (setq res nil)
  (setq rows (vla-get-Rows obj))
  (setq cols (vla-get-Columns obj))
  
  (setq j 0)
  (while (< j rows)
    (setq i 0 line nil)
    (while (< i cols)
      (setq val (vlax-variant-value (vla-GetCellValue obj j i)))
      (if val (setq val (kd:mtextstring-unformat val)) (setq val ""))
      (setq line (cons val line))
      (setq i (1+ i))
      )
    (setq res (cons (reverse line) res))
    (setq j (1+ j))
    )
  (reverse res)
  );defun
