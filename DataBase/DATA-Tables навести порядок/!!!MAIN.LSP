(load (strcat #lisppath "DATA-Tables/ziplist.lsp"))
(load (strcat #lisppath "strings\\lisplist.LSP"))
(load (strcat #lisppath "strings\\strcut.LSP"))
(load (strcat #lisppath "common functions\\ss-to-tbl.LSP"))
(load (strcat #lisppath "common functions\\ss-odd.LSP"))


;;;;;============================================================================================
;;;;;============================================================================================
;;; заполняем нужные нам элементы текстов маской
;;;;;============================================================================================
;;;;;============================================================================================
(defun mtxtfill (/ lst)
  (setq lst (mapcar 'vlax-ename->vla-object (ss->list* (ssget))))
  (mapcar '(lambda (x) (vla-put-textstring x "####")) lst)
  );defun
(mtxtfill)
;;;;;============================================================================================
;;;;;============================================================================================
;;;;;============================================================================================




;;;;;============================================================================================
;;;;;============================================================================================
;((a b c) (1 2 3) (x y z)) ====>>> ((a 1 x) (b 2 y) (c 3 z))
(defun transform (lst)
  (apply 'mapcar (append '(list) lst))
  );defun
;;;;;============================================================================================
;;;;;============================================================================================





;;;;;============================================================================================
;;;;;============================================================================================
;;; формируем ассоциативный список (таблицу) элементов которые будем заполнять
;;; lst1  - это позиции по которым будем ориентироваться в базе данных и
;;; относительно них будем заполнять lst2
(setq lst1 (mapcar '(lambda (x) (vla-get-textstring (vlax-ename->vla-object x))) (ss->list (ssget))))
(setq lst2 (mapcar 'vlax-ename->vla-object (ss->list (ssget))))
;;;; data - (("UA101" obj1) ("UA102" obj2) ...)
(setq data (mapcar '(lambda (x y) (list x y)) lst1 lst2))
;;;;;============================================================================================
;;;;;============================================================================================




;;;;;;;;============================================================================================
;;;;;;;;============================================================================================
;;;;(setq t_head '("ID" "Description"))
;;;(setq t_head '("name" "from" "to"))
;;;(defun mk_t_corr ( head / data)
;;;  (setq data '())
;;;  (foreach param head
;;;    (setq data (append data (list
;;;	(mapcar '(lambda (x) (vla-get-textstring (vlax-ename->vla-object x))) (ss->list (ssget '((0 . "*TEXT")))))
;;;	)))
;;;    );foreach
;;;  (transform data)
;;;  );defun
;;;;;;;;============================================================================================
;;;;;;;;============================================================================================
;;;(defun mk_t_objs ( head / data)
;;;  (setq data '())
;;;  (foreach param head
;;;    (setq data (append data (list
;;;	(mapcar '(lambda (x) (vlax-ename->vla-object x)) (ss->list (ssget '((0 . "*TEXT")))))
;;;	)))
;;;    );foreach
;;;  (transform data)
;;;  );defun
;;;;====================================
;;;(setq dest-table (mk_t_objs t_head))
;;;;(mapcarx vla-get-TextString nil dest-table) = mk_t_corr
;;;;====================================
;;;;;;;;============================================================================================
;;;;;;;;============================================================================================




;;;;;;;;============================================================================================
;;;;;;;;============================================================================================
;;;(setq t_head '("ID" "name"))
;;;(setq ID-name (mapcarx vla-get-TextString nil (mk_t_objs t_head)))
;;;
;;;(setq t_head '("ID"))
;;;;(setq tbl (mk_t_objs t_head))
;;;(mapcar '(lambda (x)
;;;	   (vla-put-textstring (car x) (cadr (assoc (vla-get-textstring (car x)) ID-name)))
;;;	   )(mk_t_objs t_head))
;;;;;;;;============================================================================================
;;;;;;;;============================================================================================





;====================================;====================================;====================================
;====================================;====================================;====================================
;====================================;====================================;====================================
(defun mk_t_cons ( / lout ass)
  (setq lout '())
  (while (setq ass (car (entsel)))
    (setq lout (append lout
		   (list (cons
		       (vla-get-textstring (vlax-ename->vla-object ass))
		       (mapcar '(lambda (x) (vla-get-textstring (vlax-ename->vla-object x))) (ss->list* (ssget)))
		       )))))
  lout
);defun
;;;;;============================================================================================
;;;;;============================================================================================
(setq shkafy (mk_t_cons))
;====================================
;shkafy
;(("Сборка задвижек \"250Н\",\nШ-2" "UA330" "UA329" "UA317" "UA313" "UA309" "UA325" "UA321" "UA305" "UA301") ("Сборка задвижек \"250Н\",\nШ-3" "UA365" "UA361" "UA357" "UA353" "UA349" "UA345" "UA338" "UA337") ("Сборка задвижек \"250Н\",\nШ-4" "UA332" "UA331" "UA318" "UA314" "UA310" "UA326" "UA322" "UA306" "UA302") ("Сборка задвижек \"250Н\",\nШ-5" "UA366" "UA362" "UA358" "UA354" "UA350" "UA346" "UA340" "UA339") ("Сборка задвижек \"250Н\",\nШ-6" "UA371") ("Сборка задвижек \"260Н\",\nШ-5" "UA368" "UA364" "UA360" "UA356" "UA352" "UA348" "UA344" "UA343") ("Сборка задвижек \"260Н\",\nШ-4" "UA336" "UA335" "UA320" "UA316" "UA312" "UA328" "UA324" "UA308" "UA304") ("Сборка задвижек \"260Н\",\nШ-6" "UA370" "UA369") ("Сборка задвижек \"260Н\",\nШ-3" "UA367" "UA363" "UA359" "UA355" "UA351" "UA347" "UA342" "UA341") ("Сборка задвижек \"260Н\",\nШ-2" "UA334" "UA333" "UA319" "UA315" "UA311" "UA327" "UA323" "UA307" "UA303"))
;;;;;============================================================================================
;;;;;============================================================================================
(mapcar '(lambda (x)
	   (mapcar '(lambda (it)
		      (list it (car x))
		      )
	     (cdr x)
	    ))
	   shkafy)
;====================================
;====================================
;====================================
;;;;;============================================================================================
;;;;;============================================================================================




(setq shkafy (vl-sort shkafy '(lambda (a b) (< (car a)(car b)))))
(mapcar '(lambda (x) (vl-sort (x) '(lambda (a b) (< a b)))) shkafy)













;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
(defun cols-to-array (nkol / main i)
  (setq	main '()
	i    1)
  (repeat nkol
    (alert (strcat "указываем столбец N " (itoa i)))
    (setq main (append main
	(list (mapcar '(lambda (x) (cdr (assoc 1 (entget x))))
		      (ss->list (ssget '((0 . "*TEXT"))))))))
    (princ (strcat "\n !!!!!!!!!!!!!!!!!!!!!!!!!     выбрано "
		   (itoa (length (reverse (car main))))
		   " объектов   !!!!!!!!!!!!!!!\n"))
    (setq i (1+ i)))
  ;(matrix-trans main)
  (transform main)
);defun
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;; то же только с объектами
(defun objs-to-array (nkol / main)
  (setq main '())
  (repeat nkol
    (alert "указываем столбец объектов")
    (setq main (append main
       (list (mapcar 'vlax-ename->vla-object (ss->list (ssget '((0 . "*TEXT"))))))))
    (princ "\n !!!!!!!!!!!!!!!!!!!!!!!!!     закончили выбор           !!!!!!!!!!!!!!!\n")
    )
  ;(matrix-trans main)
  (transform main)
  );defun
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;

(setq poz:base (ss->tbl (ssget '((0 . "*TEXT")))))
(setq poz:base (mapcar 'car poz:base))

;(setq cursigs (ss->lsto* (ssget '((0 . "*TEXT")))))

;(setq item (vlax-ename->vla-object (car (entsel))))


(defun c:wef ()
  (setq cursigs (ss->lsto* (ssget '((0 . "*TEXT")))))
  (vla-SetRGB #color 250 100 100)
(foreach item cursigs
  (if (setq n (member (vla-get-textstring item) (mapcar 'vla-get-textstring poz:base)))
    (progn
      (setq n (- (length poz:base)  (length n)))
      (vla-put-truecolor item #color)
      (vla-put-truecolor (nth n poz:base) #color)
      )
    )
  )
  )

;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;
