%< >%

\AcObjProp
\AcObjProp Object
\AcExpr
\AcVar



;;; добавить к строке 33333
 \f "%ps[,33333]"
%<\AcObjProp Object(%<\_ObjId 2126277048>%).TextString \f "%ps[,wow]">%

;;;  обрыв строки после точки
\f "%fn2"
%<\AcObjProp Object(%<\_ObjId 2126238752>%).TextString \f "%fn2">%

;;;  строка после точки
\f "%fn4"
%<\AcObjProp Object(%<\_ObjId 2126238752>%).TextString \f "%fn4">%


tc - text case
tc1 tc2 tc3 tc4




(vla-get-objectID (vlax-ename->vla-object (car (nentsel))))

2126238752
%<\AcObjProp Object(%<\_ObjId 2126238752>%).TextString \f "%fn2">%

















(%<\AcObjProp Object(%<\_ObjId 2126238752>%).TextString>%)
%<\AcObjProp Object(%<\_ObjId 2126277048>%).Rotation \f "%au1">%



%<\AcObjProp Object(%<\_ObjId 2126238752>%).TextString \f "%tc1">%
%<\AcObjProp Object(%<\_ObjId 2126238752>%).TextString \lisp "(strcat % \"2\")">%

%<\AcExpr (Table(%<\_ObjId 2126276856>%).Evaluate(Sum(A2:B2)))>%


%<\AcExpr (Text(%<\_ObjId 2126277048>%).Content)>%
