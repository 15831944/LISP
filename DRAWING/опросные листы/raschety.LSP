(load (strcat #lisppath "Files/file-to-list.LSP"))
(load (strcat #lisppath "specification/spclib.lsp"))

(setq fpath (kd:getfiledlg "D:\\"))
(setq lst (file-to-list fpath))












(setq punits '("Па" "кПа" "МПа" "бар" "кгс/см2" "кгс/м2" "мм рт. ст." "мм вод. ст."))
(defun calc-pabs () 
  (cond
    ((= (nth (atoi (nth 44 lst)) punits) "мм рт. ст.")
     (+ (atof* (nth 60 lst)) (/ (* (atoi (nth 59 lst)) 133.322368) 1000000)))
    )
       
  );defun


("Название измерительного комплекса" "###" "")
("Позиция по проекту" "###" "")
("Номер расчета" (nth 440 lst) "")
("Выполнен в соответствии с" "ГОСТ 8.586.(1-5)-2005" "")
("Наименование измеряемой среды" (nth (atoi (nth 41 lst)) '("Природный газ" "Вода" "Перегретый пар" "Воздух" "Азот" "Диоксид углерода" "Аммиак" "Ацетилен" "Насыщенный пар" "Другая измеряемая среда")) "")
;Агрегатное состояние вещества: Вода

("Характеристика измеряемой среды" "" "")
(list "Избыточное давление:" (nth 60 lst) (nth (atoi (nth 43 lst)) punits)) ; ???*?? кПа вмето МПа
("Барометрическое давление:" (nth 59 lst) (nth (atoi (nth 44 lst)) punits))
("Абсолютное давление:" (rtos* (calc-pabs)) "МПа")
("Температура:" (nth 57 lst) "°C")

Плотность в рабочих условиях: 924,36747 кг/м3
Динамическая вязкость: 190,51152 мкПа*с
Характеристика сужающего устройства
Тип сужающего устройства: Диафрагма с угловым способом отбора давления
Сужающее устройство: Блок с диафрагмой 02 ОСТ 108.839.02-82
Диаметр сужающего устройства при 20 °C 43,017 мм
Материал сужающего устройства Сталь 12Х18Н12Т, 12Х18Н10Т (15Х25Т)
Коэффициент линейного расширения материала сужающего устройства 1,71 Е-5 1/°C
Способ определения радиуса входной кромки измеряется
Начальный радиус закругления входной кромки 0,05 мм
Период поверки диафрагмы, в годах 2
Способ отбора давления через камеру усреднения или соединенные отверстия
Смещение оси отверстия диафрагмы относительно оси трубопровода 0 мм
Отклонение от плоскостности входного торца диафрагмы 0 мм
Характеристика трубопровода
Тип и состояние трубы вновь монтируемая
Диаметр трубопровода при 20 °C 77 мм
Материал трубопровода Сталь 20
Коэффициент линейного расширения трубопровода 1,215 Е-5 1/°C
Перепад давления 25 кПа
Массовый расход 23,1092 т/ч
Характеристика измерительного участка
1-ое местное сопротивление шаровой кран или задвижка
Расстояние от 1-го местного сопротивления до СУ 3700 мм
Длина 1-го местного сопротивления 310 мм
2-ое местное сопротивление Неопределенного вида, комбинация колен
Диаметр трубопровода между 1-ым и 2-ым местным сопротивлением 44 мм
Расстояние между 1-ым и 2-ым местным сопротивлением 260 мм
Длина 2-го местного сопротивления - мм
3-е местное сопротивление нет
Диаметр трубопровода между 2-ым и 3-им местным сопротивлением - мм
Расстояние между 2-ым и 3-им местным сопротивлением - мм
Длина 3-го местного сопротивления - мм
Расстояние между 3-им местным сопротивлением и комбинацией колен - мм
Расстояние до местного сопротивления после СУ 725 мм
Расстояние между СУ и гильзой термометра Место установки гильзы термометра после СУ 500 мм
Наружный диаметр гильзы термометра 18 мм
Первый дифманометр
Верхний предел измерения 25 кПа
Основная приведенная погрешность Функция преобразования линейная 0.25
Функция преобразования преобразователя с извлечением корня %%%
Основная приведенная погрешность преобразователя 0,1 %%%
Второй дифманометр нет
Верхний предел измерения - кПа
Основная приведенная погрешность Функция преобразования - - %%%
Функция преобразования преобразователя -
Основная приведенная погрешность преобразователя - %%%
Третий дифманометр -
Верхний предел измерения - кПа
Функция преобразования -
Основная приведенная погрешность - %%%
Функция преобразования преобразователя -
Основная приведенная погрешность преобразователя - %%%
Манометр
Верхний предел измерения 10 МПа
Основная приведенная погрешность 0,25 %%%
Основная приведенная погрешность преобразователя 0,1 %%%
Диапазон измерения манометра 700…800 мм рт. ст.
Термопреобразователь
Верхний предел измерения 200 °C
Нижний предел измерения 0 °C
Абсолютная погрешность 0,3+0,005t
Нижняя граница измерения 140 °C
Верхняя граница измерения 150 °C
Нормирующее значение расхода 25 м3/ч
