;;; изменена 12_03_21

;;; генерируем кабельынй журнал из модели

;;; -kakt00z-™  ©




;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;; принимает сроку "КВВГЭнг  3x1,5"
;;; выдает список ("КВВГЭнг" "3" "1,5")
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
(defun cbl-strtype (str / typ)
  (setq str (mapcar '(lambda (x)
		       (while (/= x (vl-string-trim " " x)) (setq x (vl-string-trim " " x)))
		       x
		       ) (sepstr str " ")))
  (setq typ (car str)
	str (cadr str))
  (setq str (sepstr str "x"))
  (list typ (car str) (cadr str))
  );defun
;(cbl-strtype str)
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;(setq cab (vlax-ename->vla-object (car (entsel))))


;;;; clist - список объектов insert "кабель" со всей модели
;;;; каждого блока кабеля должно быть по 2 - с трасс и с подключений к шкафу
;;;; во встречных блоках (один и тот же кабель) должны совпадать
;;;; номер кабеля, его тип (если нет - см переменную "errcount" )

;;;; выдает список кабелей (не блоков а именно кабелей, без повторений)
;;;; собрав информацию
;;;; вид элемента списка  (<номер-кабеля> <откуда> <куда> <тип> <жильность> <сечение>)

(defun clist->data (clst /
		    atts data cab ndata waserr out
		    ;errcount
		    )
  (setq data (mapcar '(lambda (cab)
			(mapcar 'vla-get-textstring (getbatts cab '("НомКабеля" "КУДА" "ОТОБРАЖЕНИЕ_ТИПА")))
			) clst))
  (setq ndata data
	errcount nil)

  (while ndata
    (setq waserr nil)
    (setq cab (car ndata))
    (setq cab (vl-remove-if-not '(lambda (x)
				   (= (car cab) (car x))
				   ) ndata))
    (setq ndata (vl-remove-if '(lambda (x)
				   (= (car (car cab)) (car x))
				   ) ndata))
    (if (= 2 (length cab))
      (progn
	(if (/= (caddr (car cab)) (caddr (cadr cab)))
	  (setq errcount (append errcount (list (list (car (car cab)) "не совпадает тип кабеля"))) waserr T)
	  )
      (setq cab (list
		(car (car cab))
		(cadr (car cab))
		(cadr (cadr cab))
		(caddr (car cab))
		))
      )
      (setq errcount (append errcount (list (list (car (car cab)) "кабель не парный"))) waserr T)
      );if
    (if (null waserr)
      (setq out (append out (list cab)))
      )
    );while
  (princ "\n\n\n ================  проверь переменную errcount на наличие ошибок =============\n\n")
    
  (setq out (vl-sort out '(lambda (a b)
		   (< (car a) (car b)))))
  
  (mapcar '(lambda (x / tp)
	     (setq tp (cbl-strtype (cadddr x)))
	     (list (car x) (cadr x) (caddr x) (car tp) (cadr tp) (caddr tp))
	     ) out)
  );defun
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;



;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
; список в текстоый файл (например для excell)
(defun lst->txtf (lst / fpath fhand str)
  (setq fpath "d:/spec.txt"
	fhand (open fpath "w"))
  (foreach item lst
    (setq str "")
    (foreach memb item
      (if memb
	(setq str (strcat str "\t" memb))
	(setq str (strcat str "\t")) ;"knol"))
	);if
      )
    (write-line str fhand)
    )
  (close fhand)
  );defun
;(lst->txtf (clist->data clist))
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;





;;; Select Similar на кабелях кот. нужно пронумеровать
(setq clist (ss->lsto* (ssget "_I")))
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;    НУМЕРАЦИЯ КАБЕЛЕЙ    ;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;

(setq clist (vl-sort clist '(lambda (a b)
      (>
	(cadr (vlax-safearray->list (vlax-variant-value (vla-get-InsertionPoint a))))
	(cadr (vlax-safearray->list (vlax-variant-value (vla-get-InsertionPoint b))))
	))))
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;

(setq str "CXC01-"
      i0 4001
      i 0)

(repeat (length clist)
  (vla-put-textstring (getbatt (nth i clist) "НомКабеля") (strcat str (itoa (+ i0 i))))
  (setq i (1+ i))
  )







;;; Select Similar на всех кабелях
(setq clist (ss->lsto* (ssget "_I")))
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;    ДАННЫЕ   ;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
(setq data (clist->data clist))
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;



















;;;;;;;;;;;;;;;;;;;;;;;;;;;;;;;;;;;;;;;;;;;;;;;;;;;;;;;;;;;;;;;;;;;;;;;;;;;;;;;;;;;;;;;;;;;;;;;;;;
;(load "d:\\LISP WORKING\\!blocking\\cablelist\\")
(setq ip (getpoint "\nУкажите точку вставки"))
(setq vect '(0 0 0))
(setq	bobj (vla-InsertBlock #modspace
	       (vlax-3d-point (mapcar '+ ip vect))
	       "d:\\LISP WORKING\\!blocking\\cablelist\\cl_table.dwg"
	       1 1 1 0))
(setq tbl (vla-explode bobj))
(vla-delete bobj)
(vlax-release-object bobj)
(setq bobj nil)
(setq tbl (car (vlax-safearray->list (vlax-variant-value tbl))))
;(vla-getcolumnName tbl 1)
;(vla-put-rows tbl 22)
;(vla-InsertRows tbl 2 8 5)
;(vla-InsertRows tbl 2 12 19)
;;; <номер строки начала вставки> <высота > <количество строк>

(vla-InsertRows tbl 2 12 (length data))
(vla-GenerateLayout tbl)

(setq j 1)

(foreach line data
  (vla-settext tbl j 1 (nth 0 line))
  (vla-settext tbl j 2 (nth 1 line))
  (vla-settext tbl j 3 (nth 2 line))
  (vla-settext tbl j 4 (nth 3 line))
  (vla-settext tbl j 6 (nth 4 line))
  (vla-settext tbl j 7 (nth 5 line))
  (setq j (1+ j))
  )

;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;









;;;;;;;;;;;;;;;;;;;;;;;;;;;;;;;;;;;;;;;;;;;;;;;;;;;;;;;;;;;;;;;;;;;;;;;;;;;;;;;;;;;;;;;;;;;;;;;;;;
; наигрался с таблицами , терь как в заготовке - текстами
; формируем таблицу текстов по сетке XY


; нравиццол намного больше чем варант выше
; тока надо сделать выбор objtbl одним ssget'ом, отсортироваав элементы автоматически
;data-tables

;(setq objtbl (objs-to-array 6))
(setq objtbl (ss->tbl (ssget '((0 . "*TEXT")))))
;(mapcarx vla-get-textstring nil (ss->tbl (ssget '((0 . "*TEXT")))))


(foreach line objtbl
  ;(setq line (car objtbl))
  (if (setq dt (assoc (vla-get-textstring (car line)) data))
    (mapcar '(lambda (a b)
	       (vla-put-textstring a b)
	       ) line dt)
    (princ (vla-get-textstring (car line)))
    )
  )
;;;;;;;;;;;;;;;;;;;;;;;;;;;;;;;;;;;;;;;;;;;;;;;;;;;;;;;;;;;;;;;;;;;;;;;;;;;;;;;;;;;;;;;;;;;;;;;;;;
