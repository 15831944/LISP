(load (strcat #lisppath "DataBase\\dblib.lsp"))
(load (strcat #lisppath "strings\\stringlib.lsp"))
(load (strcat #lisppath "Excel\\xlsformatlib.LSP"))

;(db|getdata)
;(setq db:head nil)
;(setq db:data nil)



;; из файла ЗРА ШК10 14_06_12.2.xlsx
;; получаем файл ЗРА ШК10 14_06_12.3.xlsx



;;  выделяем в исходном файле ВСЕ параметры и данные
(setq excdata (excel>lst))
(setq db:data (cdr excdata) db:head (car excdata))


;  обрабатываем данные
(setq comdata nil) ; - общие данные для заполнения последующих строк (общее для сигналов одной задвижки)
(setq newdata
(mapcar
  '(lambda (line)	;(setq line (nth 6 db:data))
     (cond
       ((apply '= (cons 'nil line)) (setq comdata nil) line)
       ((db|gpar "equipment" line) (setq comdata (list (list "элсх" (db|gpar "элсх" line)) (list "KKS" (db|gpar "KKS" line)) (list "equipment" (db|gpar "equipment" line)) (list "монтсх" (db|gpar "монтсх" line)) (list "place_field" (db|gpar "place_field" line)) (list "field_name" (db|gpar "field_name" line)))) line)
       ((db|gpar "sign_type" line) (db|spars line comdata))
       (T line)
       )
     )
  db:data)
      )
;;;  выводим данные в новый файл
(lst>excel newdata)
;;;   копируем из нового файла в старый
;;;   ВСЕ кроме шапки в левую верхнюю ячейку - чтобы сохранить форматирование





;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;	DIO
;;      разделение в екселевском файле когда все сигналы идут подряд
;;	отсортированные по позиции задвижки
;;	короче вставка пустой строчки между задвижками

;;         НЕ НАДО ТАК ДЕЛАТЬ КОРОЧЕ
;;  выделяем в исходном файле ВСЕ параметры и данные
(setq excdata (excel>lst))
(setq db:data (cdr excdata) db:head (car excdata))

;  параметр для разделения
(setq rptpar "KKS" cval nil)
;(setq newdata
(mapcar
  '(lambda (line)	;(setq line (nth 0 db:data))
     (cond
       ((db|gpar rptpar line)
	);;         НЕ НАДО ТАК ДЕЛАТЬ КОРОЧЕ

       
       ((apply '= (cons 'nil line)) (setq comdata nil) line)
       ((db|gpar "equipment" line) (setq comdata (list (list "элсх" (db|gpar "элсх" line)) (list "KKS" (db|gpar "KKS" line)) (list "equipment" (db|gpar "equipment" line)) (list "монтсх" (db|gpar "монтсх" line)) (list "place_field" (db|gpar "place_field" line)) (list "field_name" (db|gpar "field_name" line)))) line)
       ((db|gpar "sign_type" line) (db|spars line comdata))
       (T line)
       )
     )
  db:data
  )
;      )
;;         НЕ НАДО ТАК ДЕЛАТЬ КОРОЧЕ


















;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;
;теперь когда есть КЖ, будем заполнять сигналы номерами кабелей

(db|getdata 'db:hrad 'db:data)
(setq cbl:head db:head cbl:data db:data db:head nil db:data nil)
; убираем лишние кабели
(length cbl:data)
(setq db:head cbl:head)
(setq cbl:data (vl-remove-if-not '(lambda (line) (wcmatch (db|gpar "place_cpu" line) "*`#CTRL*")) (cdr cbl:data)))
(length cbl:data)
;'(("Клапан запорный на питательной воде до экономайзера" "эл6" "~220 В. Сигнализация" "2HS-201" "220DI" "BJH60-2002" "" "DI220#CTRL" "#РТЗО, Ш2" "КВВГнг" "6" "7" "1,5" "marks=N,A9,A11,A15,A19,A23") ("Клапан запорный на питательной воде до экономайзера" "эл6" "~220 В. Управление" "2HS-201" "220DO" "BJH60-2003" "" "DO#CTRL" "#РТЗО, Ш2" "КВВГнг" "6" "7" "1,5" "marks=A1,A16,A11,A12,A19,A20") ("Клапан запорный на питательной воде после экономайзера" "эл5" "~220 В. Сигнализация" "2HS-202" "220DI" "BJH60-2010" "" "DI220#CTRL" "#РТЗО, Ш2" "КВВГнг" "6" "7" "1,5" "marks=N,A9,A11,A15,A19,A23") ("Клапан запорный на питательной воде после экономайзера" "эл5" "~220 В. Управление" "2HS-202" "220DO" "BJH60-2011" "" "DO#CTRL" "#РТЗО, Ш2" "КВВГнг" "6" "7" "1,5" "marks=A1,A16,A11,A12,A19,A20") ("Клапан запорный на трубопроводе в бак питводы" "эл5" "~220 В. Сигнализация" "2HS-203" "220DI" "BJH60-2013" "" "DI220#CTRL" "#РТЗО, Ш2" "КВВГнг" "6" "7" "1,5" "marks=N,A9,A11,A15,A19,A23") ("Клапан запорный на трубопроводе в бак питводы" "эл5" "~220 В. Управление" "2HS-203" "220DO" "BJH60-2014" "" "DO#CTRL" "#РТЗО, Ш2" "КВВГнг" "6" "7" "1,5" "marks=A1,A16,A11,A12,A19,A20") ("Клапан запорный на линии впрыска в п/о" "эл5" "~220 В. Сигнализация" "2HS-204" "220DI" "BJH60-2016" "" "DI220#CTRL" "#РТЗО, Ш2" "КВВГнг" "6" "7" "1,5" "marks=N,A9,A11,A15,A19,A23") ("Клапан запорный на линии впрыска в п/о" "эл5" "~220 В. Управление" "2HS-204" "220DO" "BJH60-2017" "" "DO#CTRL" "#РТЗО, Ш2" "КВВГнг" "6" "7" "1,5" "marks=A1,A16,A11,A12,A19,A20") ("Клапан регулирующий на линии впрыска в п/о" "эл3" "4…20 мА. Положение" "2HS-205" "420AI+" "BJH60-5004" "" "AI#CTRL" "#РТЗО, Ш3" "КВВГЭнг" "2" "4" "1,5" "marks=16,18") ("Клапан регулирующий на линии впрыска в п/о" "эл3" "24 В. Сигнализация" "2HS-205" "24DI" "BJH60-5002" "" "DI24#CTRL" "#РТЗО, Ш3" "КВВГЭнг" "3" "5" "1,5" "marks=8,17,19") ("Клапан регулирующий на линии впрыска в п/о" "эл3" "24 В. Управление" "2HS-205" "24DO" "BJH60-5003" "" "DO#CTRL" "#РТЗО, Ш3" "КВВГЭнг" "4" "5" "1,5" "marks=7,9,17,19") ("Клапан запорный на аварийном сливе из барабана" "эл5" "~220 В. Сигнализация" "2HS-206" "220DI" "BJH60-2019" "" "DI220#CTRL" "#РТЗО, Ш2" "КВВГнг" "6" "7" "1,5" "marks=N,A9,A11,A15,A19,A23") ("Клапан запорный на аварийном сливе из барабана" "эл5" "~220 В. Управление" "2HS-206" "220DO" "BJH60-2020" "" "DO#CTRL" "#РТЗО, Ш2" "КВВГнг" "6" "7" "1,5" "marks=A1,A16,A11,A12,A19,A20") ("Клапан запорный на непрерывной продувке" "эл5" "~220 В. Сигнализация" "2HS-207" "220DI" "BJH60-2022" "" "DI220#CTRL" "#РТЗО, Ш2" "КВВГнг" "6" "7" "1,5" "marks=N,A9,A11,A15,A19,A23") ("Клапан запорный на непрерывной продувке" "эл5" "~220 В. Управление" "2HS-207" "220DO" "BJH60-2023" "" "DO#CTRL" "#РТЗО, Ш2" "КВВГнг" "6" "7" "1,5" "marks=A1,A16,A11,A12,A19,A20") ("Клапан запорный на продувке пароперегревателя" "эл7" "~220 В. Сигнализация" "2HS-208" "220DI" "BJH60-2006" "" "DI220#CTRL" "#РТЗО, Ш2" "КВВГнг" "6" "7" "1,5" "marks=N,A9,A11,A15,A19,A23") ("Клапан запорный на продувке пароперегревателя" "эл7" "~220 В. Управление" "2HS-208" "220DO" "BJH60-2007" "" "DO#CTRL" "#РТЗО, Ш2" "КВВГнг" "6" "7" "1,5" "marks=A1,A16,A11,A12,A19,A20") ("Задвижка на паре от котла (ГПЗ)" "эл8" "~220 В. Сигнализация" "2HS-209" "220DI" "BJH60-2026" "" "DI220#CTRL" "#РТЗО, Ш2" "КВВГнг" "6" "7" "1,5" "marks=N,A9,A11,A15,A19,A23") ("Задвижка на паре от котла (ГПЗ)" "эл8" "~220 В. Управление" "2HS-209" "220DO" "BJH60-2027" "" "DO#CTRL" "#РТЗО, Ш2" "КВВГнг" "6" "7" "1,5" "marks=A1,A11,A12,A16,A19,A20") ("Клапан запорный на паре на разогрев барабана" "эл5" "~220 В. Сигнализация" "2HS-210" "220DI" "BJH60-2029" "" "DI220#CTRL" "#РТЗО, Ш2" "КВВГнг" "6" "7" "1,5" "marks=N,A9,A11,A15,A19,A23") ("Клапан запорный на паре на разогрев барабана" "эл5" "~220 В. Управление" "2HS-210" "220DO" "BJH60-2030" "" "DO#CTRL" "#РТЗО, Ш2" "КВВГнг" "6" "7" "1,5" "marks=A1,A16,A11,A12,A19,A20") ("Клапан регулирующий перед ВП горячей ступени" "эл2" "4…20 мА. Положение" "2HS-300" "420AI+" "BJH60-5028" "" "AI#CTRL" "#УКП" "КВВГЭнг" "2" "4" "1,5" "marks=16,18") ("Клапан регулирующий перед ВП горячей ступени" "эл2" "24 В. Сигнализация" "2HS-300" "24DI" "BJH60-5026" "" "DI24#CTRL" "#РТЗО, Ш4" "КВВГЭнг" "3" "5" "1,5" "marks=8,17,19") ("Клапан регулирующий перед ВП горячей ступени" "эл2" "24 В. Управление" "2HS-300" "24DO" "BJH60-5027" "" "DO#CTRL" "#РТЗО, Ш4" "КВВГЭнг" "4" "5" "1,5" "marks=7,9,17,19") ("Клапан регулирующий на байпасе ВП горячей ступени" "эл2" "4…20 мА. Положение" "2HS-301" "420AI+" "BJH60-5032" "" "AI#CTRL" "#УКП" "КВВГЭнг" "2" "4" "1,5" "marks=16,18") ("Клапан регулирующий на байпасе ВП горячей ступени" "эл2" "24 В. Сигнализация" "2HS-301" "24DI" "BJH60-5030" "" "DI24#CTRL" "#РТЗО, Ш4" "КВВГЭнг" "3" "5" "1,5" "marks=8,17,19") ("Клапан регулирующий на байпасе ВП горячей ступени" "эл2" "24 В. Управление" "2HS-301" "24DO" "BJH60-5031" "" "DO#CTRL" "#РТЗО, Ш4" "КВВГЭнг" "4" "5" "1,5" "marks=7,9,17,19") ("Клапан регулирующий на байпасе ВП холодной ступени" "эл2" "4…20 мА. Положение" "2HS-303" "420AI+" "BJH60-5036" "" "AI#CTRL" "#УКП" "КВВГЭнг" "2" "4" "1,5" "marks=16,18") ("Клапан регулирующий на байпасе ВП холодной ступени" "эл2" "24 В. Сигнализация" "2HS-303" "24DI" "BJH60-5034" "" "DI24#CTRL" "#РТЗО, Ш4" "КВВГЭнг" "3" "5" "1,5" "marks=8,17,19") ("Клапан регулирующий на байпасе ВП холодной ступени" "эл2" "24 В. Управление" "2HS-303" "24DO" "BJH60-5035" "" "DO#CTRL" "#РТЗО, Ш4" "КВВГЭнг" "4" "5" "1,5" "marks=7,9,17,19") ("Клапан регулирующий после ВП холодной ступени" "эл2" "4…20 мА. Положение" "2HS-304" "420AI+" "BJH60-5040" "" "AI#CTRL" "#УКП" "КВВГЭнг" "2" "4" "1,5" "marks=16,18") ("Клапан регулирующий после ВП холодной ступени" "эл2" "24 В. Сигнализация" "2HS-304" "24DI" "BJH60-5038" "" "DI24#CTRL" "#РТЗО, Ш4" "КВВГЭнг" "3" "5" "1,5" "marks=8,17,19") ("Клапан регулирующий после ВП холодной ступени" "эл2" "24 В. Управление" "2HS-304" "24DO" "BJH60-5039" "" "DO#CTRL" "#РТЗО, Ш4" "КВВГЭнг" "4" "5" "1,5" "marks=7,9,17,19") ("Клапан регулирующий на сопла вторичного дутья" "эл2" "4…20 мА. Положение" "2HS-333" "420AI+" "BJH60-5044" "" "AI#CTRL" "#УКП" "КВВГЭнг" "2" "4" "1,5" "marks=16,18") ("Клапан регулирующий на сопла вторичного дутья" "эл2" "24 В. Сигнализация" "2HS-333" "24DI" "BJH60-5042" "" "DI24#CTRL" "#РТЗО, Ш4" "КВВГЭнг" "3" "5" "1,5" "marks=8,17,19") ("Клапан регулирующий на сопла вторичного дутья" "эл2" "24 В. Управление" "2HS-333" "24DO" "BJH60-5043" "" "DO#CTRL" "#РТЗО, Ш4" "КВВГЭнг" "4" "5" "1,5" "marks=7,9,17,19") ("Клапан регулирующий первичного воздуха" "эл2" "4…20 мА. Положение" "2HS-334" "420AI+" "BJH60-5048" "" "AI#CTRL" "#УКП" "КВВГЭнг" "2" "4" "1,5" "marks=16,18") ("Клапан регулирующий первичного воздуха" "эл2" "24 В. Сигнализация" "2HS-334" "24DI" "BJH60-5046" "" "DI24#CTRL" "#РТЗО, Ш4" "КВВГЭнг" "3" "5" "1,5" "marks=8,17,19") ("Клапан регулирующий первичного воздуха" "эл2" "24 В. Управление" "2HS-334" "24DO" "BJH60-5047" "" "DO#CTRL" "#РТЗО, Ш4" "КВВГЭнг" "4" "5" "1,5" "marks=7,9,17,19") ("Клапан регулирующий на газоходе рециркуляции дымовых газов" "эл2" "4…20 мА. Положение" "2HS-450" "420AI+" "BJH60-5052" "" "AI#CTRL" "#УКП" "КВВГЭнг" "2" "4" "1,5" "marks=16,18") ("Клапан регулирующий на газоходе рециркуляции дымовых газов" "эл2" "24 В. Сигнализация" "2HS-450" "24DI" "BJH60-5050" "" "DI24#CTRL" "#РТЗО, Ш4" "КВВГЭнг" "3" "5" "1,5" "marks=8,17,19") ("Клапан регулирующий на газоходе рециркуляции дымовых газов" "эл2" "24 В. Управление" "2HS-450" "24DO" "BJH60-5051" "" "DO#CTRL" "#РТЗО, Ш4" "КВВГЭнг" "4" "5" "1,5" "marks=7,9,17,19") ("Направляющий аппарат дымососа" "эл2" "4…20 мА. Положение" "2HS-500" "420AI+" "BJH60-5008" "" "AI#CTRL" "#УКП" "КВВГЭнг" "2" "4" "1,5" "marks=16,18") ("Направляющий аппарат дымососа" "эл2" "24 В. Сигнализация" "2HS-500" "24DI" "BJH60-5006" "" "DI24#CTRL" "#РТЗО, Ш3" "КВВГЭнг" "3" "5" "1,5" "marks=8,17,19") ("Направляющий аппарат дымососа" "эл2" "24 В. Управление" "2HS-500" "24DO" "BJH60-5007" "" "DO#CTRL" "#РТЗО, Ш3" "КВВГЭнг" "4" "5" "1,5" "marks=7,9,17,19") ("Направляющий аппарат дымососа рециркуляции №1" "эл2" "4…20 мА. Положение" "2HS-501" "420AI+" "BJH60-5012" "" "AI#CTRL" "#УКП" "КВВГЭнг" "2" "4" "1,5" "marks=16,18") ("Направляющий аппарат дымососа рециркуляции №1" "эл2" "24 В. Сигнализация" "2HS-501" "24DI" "BJH60-5010" "" "DI24#CTRL" "#РТЗО, Ш3" "КВВГЭнг" "3" "5" "1,5" "marks=8,17,19") ("Направляющий аппарат дымососа рециркуляции №1" "эл2" "24 В. Управление" "2HS-501" "24DO" "BJH60-5011" "" "DO#CTRL" "#РТЗО, Ш3" "КВВГЭнг" "4" "5" "1,5" "marks=7,9,17,19") ("Направляющий аппарат дымососа рециркуляции №2" "эл2" "4…20 мА. Положение" "2HS-502" "420AI+" "BJH60-5016" "" "AI#CTRL" "#УКП" "КВВГЭнг" "2" "4" "1,5" "marks=16,18") ("Направляющий аппарат дымососа рециркуляции №2" "эл2" "24 В. Сигнализация" "2HS-502" "24DI" "BJH60-5014" "" "DI24#CTRL" "#РТЗО, Ш3" "КВВГЭнг" "3" "5" "1,5" "marks=8,17,19") ("Направляющий аппарат дымососа рециркуляции №2" "эл2" "24 В. Управление" "2HS-502" "24DO" "BJH60-5015" "" "DO#CTRL" "#РТЗО, Ш3" "КВВГЭнг" "4" "5" "1,5" "marks=7,9,17,19") ("Направляющий аппарат вентилятора общего воздуха" "эл2" "4…20 мА. Положение" "2HS-503" "420AI+" "BJH60-5020" "" "AI#CTRL" "#УКП" "КВВГЭнг" "2" "4" "1,5" "marks=16,18") ("Направляющий аппарат вентилятора общего воздуха" "эл2" "24 В. Сигнализация" "2HS-503" "24DI" "BJH60-5018" "" "DI24#CTRL" "#РТЗО, Ш3" "КВВГЭнг" "3" "5" "1,5" "marks=8,17,19") ("Направляющий аппарат вентилятора общего воздуха" "эл2" "24 В. Управление" "2HS-503" "24DO" "BJH60-5019" "" "DO#CTRL" "#РТЗО, Ш3" "КВВГЭнг" "4" "5" "1,5" "marks=7,9,17,19") ("Направляющий аппарат вентилятора первичного воздуха" "эл2" "4…20 мА. Положение" "2HS-504" "420AI+" "BJH60-5024" "" "AI#CTRL" "#УКП" "КВВГЭнг" "2" "4" "1,5" "marks=16,18") ("Направляющий аппарат вентилятора первичного воздуха" "эл2" "24 В. Сигнализация" "2HS-504" "24DI" "BJH60-5022" "" "DI24#CTRL" "#РТЗО, Ш3" "КВВГЭнг" "3" "5" "1,5" "marks=8,17,19") ("Направляющий аппарат вентилятора первичного воздуха" "эл2" "24 В. Управление" "2HS-504" "24DO" "BJH60-5023" "" "DO#CTRL" "#РТЗО, Ш3" "КВВГЭнг" "4" "5" "1,5" "marks=7,9,17,19") ("Клапан запорный на газе к котлу" "эл10" "~220 В. Сигнализация" "2HS-601" "220DI" "BJH60-2045" "" "DI220#CTRL" "#РТЗО, Ш5" "КВВГнг" "6" "7" "1,5" "marks=N,A15,A19,A23,A8,A9") ("Клапан запорный на газе к котлу" "эл10" "~220 В. Управление" "2HS-601" "220DO" "BJH60-2046" "" "DO#CTRL" "#РТЗО, Ш5" "КВВГнг" "6" "7" "1,5" "marks=A1,A11,A12,A16,A20,A24") ("Клапан отсечной на газе к котлу" "эл9" "~220 В. Сигнализация" "2HS-602" "220DI" "BJH60-2048" "" "DI220#CTRL" "#РТЗО, Ш5" "КВВГнг" "6" "7" "1,5" "marks=A10,A2,A3,A9,N") ("Клапан отсечной на газе к котлу" "эл9" "~220 В. Управление" "2HS-602" "220DO" "BJH60-2049" "" "DO#CTRL" "#РТЗО, Ш5" "КВВГнг" "6" "7" "1,5" "marks=16,18,A11,A12,A4 ") ("Клапан регулирующий на газе к котлу" "эл4" "4…20 мА. Положение" "2HS-603" "420AI+" "BJH60-5056" "" "AI#CTRL" "#УКП" "КВВГЭнг" "2" "4" "1,5" "marks=16,18") ("Клапан регулирующий на газе к котлу" "эл4" "24 В. Сигнализация" "2HS-603" "24DI" "BJH60-5054" "" "DI24#CTRL" "#РТЗО, Ш5" "КВВГЭнг" "3" "5" "1,5" "marks=8,17,19") ("Клапан регулирующий на газе к котлу" "эл4" "24 В. Управление" "2HS-603" "24DO" "BJH60-5055" "" "DO#CTRL" "#РТЗО, Ш5" "КВВГЭнг" "4" "5" "1,5" "marks=7,9,17,19"))
;  64 кабеля идет в контроллер из 106
; это из тех которые относятся к арматуре

; ориглист по позиции задвижки = количество арматуры
(length (origlist (mapcar '(lambda (x) (db|gpar "poz" x)) cbl:data)))
cbl:data
(setq db:head nil)
;; закрываем КЖ



;;  выделяем в исходном файле ВСЕ параметры и данные
(setq excdata (excel>lst))
(setq db:data (cdr excdata) sig:head (car excdata))

;  обрабатываем данные


(setq newdata
(mapcar
  '(lambda (sig / kks st ccab csigs)	;(setq sig (nth 0 db:data))
     (defun marktos (mrk)
       (cond
	 ((= (type mrk) 'REAL) (itoa (fix mrk)))
	 ((= (type mrk) 'STR) (vl-string-trim " " mrk))
	 ((= (type mrk) 'INT) (itoa mrk))
	 )
       )
     (setq db:head sig:head)
     (if (setq kks (db|gpar "KKS" sig) st (db|gpar "sign_type" sig))
       (progn
	 (setq db:head cbl:head)
	 (setq ccab (db|filter (db|filter cbl:data (strcat "poz=" kks)) (strcat "sign_type=" st)))
	 (if (= 1 (length ccab))
	   (progn
	     (setq ccab (car ccab))
	     (setq ccab (mapcar 'list cbl:head ccab))
	     (setq csigs (mapcar 'marktos (cdr (assoc "marks" (vcfstr>data (cadr (assoc "remarks" ccab)))))))
	     (setq db:head sig:head)
	     ;проверка на совпадение марок связей в кабеле и сигнале
	     (if (null (and (member (marktos (db|gpar "mark1" sig)) csigs) (member (marktos (db|gpar "mark2" sig)) csigs)))
	       (exit))
	     (setq db:head sig:head)
	     (db|spars
	       sig
	       (list
		 (list "cbl_KKS" (cadr (assoc "cbl_KKS" ccab)))
		 (list "cab_type" (cadr (assoc "cab_type" ccab)))
		 (list "cores" (cadr (assoc "cores_cab" ccab)))
		 (list "section" (cadr (assoc "section" ccab)))
		 )
	       )
	     )
	   (exit)
	   )
	 )
       sig
       )
     )
  db:data
  )
)


;;;  выводим данные в новый файл
(lst>excel newdata)
;;;   копируем из нового файла в старый
;;;   ВСЕ кроме шапки в левую верхнюю ячейку - чтобы сохранить форматирование




;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;   сравнение 2-х excel-файлов   ;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

;; если надо только заполненные (информативные) данные

;;  открываем 1-й файл
(db|getdata)
(setq pered:head db:head pered:data db:data db:head nil db:data nil)
(1- (length pered:data))

;;  открываем 2-й файл
(db|getdata)
(setq posle:head db:head posle:data db:data db:head nil db:data nil)
(1- (length posle:data))



(setq ans (mapcar 'equal pered:data posle:data))
(length (vl-remove 'T ans))


(setq lst nil)
(mapcar
  '(lambda (pe po)
     (if (null (equal pe po))
       ;(setq lst (append lst (list pe)))
       (setq lst (cons pe lst))
       )
     )
  pered:data posle:data)
(setq lst (reverse lst))

(lst>excel (cons pered:head lst))








;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;















;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;


;;;;;;;;;;;;;;;;;;;          работа 2
;; есть файл ексель "1 ШК20 14_04_02.xlsx" - подключение к контроллеру первого котла
;; есть второй файл - с сигналами для второго котла , часть из которых совпадают с первым
;; задача - заполнить номера клемм вт

;;;
;;;(str|compare
;;;  (vla-get-TextString (vlax-ename->vla-object (car (nentsel))))
;;;  (vla-get-TextString (vlax-ename->vla-object (car (nentsel))))
;;;  )



;;  открываем файл первого котла, выделяем всё значимое и выполняем:
(db|getdata)
(setq cbnt20:head db:head cbnt20:data db:data db:head nil db:data nil)
;;  закрываем 1-й шкаф


; консолидируем данные по сцепке параметров event+equipment+meas_name
(setq db:head cbnt20:head)
(setq K1data (db|mapzip* cbnt20:data '("event" "equipment" "meas_name"))) (setq db:head nil)
;(car K1data)
;(nth 354 K1data)
;; база знаний создана, закрываем файл



;;  открываем файл второго котла,
;;  выделяем все, даже с пустыми строчками и выполняем:
(setq excdata (excel>lst))
(setq db:data (cdr excdata) db:head (car excdata))
;; база исходных данных создана



;  обрабатываем данные
(setq newdata
(mapcar
  '(lambda (line / comparestring data)	;(setq line (nth 16 db:data))
     (setq db:head (car excdata))
     (setq comparestring (subst "" nil (list (db|gpar "event" line) (db|gpar "equipment" line) (db|gpar "meas_name" line))))
     (setq comparestring (antisep comparestring ""))
     (if (setq data (cadr (assoc comparestring (cdr K1data))))
       (progn
	 (setq db:head cbnt20:head)
	 (setq data (list (list "cabinet" (db|gpar "cabinet" data)) (list "clamp" (db|gpar "clamp" data)) (list "relay" (db|gpar "relay" data)) (list "cl1" (db|gpar "cl1" data))(list "cl2" (db|gpar "cl2" data))))
	 (setq db:head (car excdata))
	 (db|spars line data)
	 )
       line
       )
     )
  db:data)
      )
;;;  выводим данные в новый файл
(lst>excel newdata)
;;;   копируем из нового файла в старый, выбираем только значения
;;;   ВСЕ кроме шапки в левую верхнюю ячейку - чтобы сохранить форматирование




;(mapcar 'str|compare-SoundexWordEncodeRU (sepstr (vla-get-TextString (vlax-ename->vla-object (car (nentsel)))) " "))
