;;;;; ÒÊÏ 45-4.02-129-2009 
(setq #ÒÊÏ45-4.02-129-2009 '(
	(50	75	100	125	150	175	200	225	250	275	300	325	350	375	400	425	450	475	500	525	550	575	600)
(57	(44	58	68	78	87	94	101	108	117	123	128	136	145	150	154	159	163	169	178	180	185	189	195))
(76	(44	62	74	83	91	100	109	116	124	133	141	147	154	158	164	170	178	184	192	194	196	203	211))
(89	(47	64	77	87	95	104	113	120	128	136	145	152	158	163	168	176	184	187	194	200	206	211	216))
(108	(51	68	80	90	100	110	119	126	133	142	152	157	164	170	176	182	190	195	201	207	214	219	224))
(133	(53	70	82	94	105	115	124	134	143	151	158	164	170	178	187	192	199	203	210	217	223	229	234))
(159	(54	74	88	99	110	119	128	138	149	156	163	170	178	185	194	199	205	212	221	226	232	239	245))
(219	(58	78	92	104	115	128	140	149	158	166	175	182	191	198	206	214	222	227	234	241	249	255	261))
(273	(59	84	96	109	121	133	144	153	163	173	183	191	198	206	215	223	230	237	245	252	259	267	274))
(325	(62	83	97	112	127	138	148	158	168	178	188	196	205	214	223	231	239	246	255	261	268	276	284))
(377	(61	84	100	116	130	141	152	163	173	183	193	202	211	220	229	236	244	252	262	269	276	283	291))
(426	(63	86	102	117	131	144	156	167	178	187	197	206	216	224	234	242	250	258	267	276	284	291	298))
(478	(64	88	104	120	134	146	158	170	181	191	201	211	220	230	240	248	257	265	273	282	291	299	307))
(530	(64	89	107	122	135	148	160	172	184	194	203	214	225	233	242	252	261	269	277	286	295	303	312))
(630	(66	90	109	124	139	153	166	177	188	199	210	220	230	240	250	259	268	277	287	295	303	312	320))
(720	(66	91	109	126	141	155	168	179	191	202	214	224	235	245	255	264	274	283	293	302	311	319	328))
(820	(68	93	111	128	143	157	170	183	195	207	218	229	239	249	260	270	280	289	298	307	317	326	335))
(920	(69	94	112	129	145	159	173	185	197	209	221	232	243	253	264	274	284	293	303	313	322	332	342))
(1020	(68	95	113	131	147	161	175	188	200	212	224	235	247	257	267	278	288	298	309	318	327	337	347))
(1220	(69	96	115	133	148	163	177	190	203	216	228	239	251	262	273	283	294	304	315	325	335	345	355))
(1420	(69	98	117	134	149	165	179	192	205	218	231	242	254	265	276	287	298	309	320	330	340	350	360))
	    ))


;;;(setq tmpr 145)
;;;(setq diam 100)
;;;
;;;(vl-position (get-closer-from-row tmpr (car lst)) (car lst))
;;;
;;;(defun 
;;;(nth
;;;  (vl-position (get-closer-from-row tmpr (car lst)) (car lst))
;;;  (cadr
;;;    (assoc
;;;      (get-closer-from-row diam (mapcar 'car (cdr lst)))
;;;      (cdr lst)))
;;;  )
;;;
;;;
