; 14_12_12
; СВТУ



; генерация списка - части параграфа спецификации
;;;;;;;;;;;;;;;;;;;;;;;;;;;;;;;;;;;;;;;;;;;;;;;;;;;;;;;
;;;;;;;;;;;;;;;;;;;;;;;;;;;;;;;;;;;;;;;;;;;;;;;;;;;;;;;






;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;     Р  У     ;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
(setq #SVTU|RUlist
   '(
     (20 "РУ-20" 0.06 0.12 6)
     (32 "РУ-32" 0.22 0.6 22)
     (50 "РУ-50" 0.7 1.4 70)
     (65 "РУ-65" 1.2 2.4 120)
     (80 "РУ-80" 1.8 3.6 180)
     (100 "РУ-100" 2.8 5.7 280)
     (125 "РУ-125" 4.5 8.8 450)
     (150 "РУ-150" 6.5 12.7 650)
     (200 "РУ-200" 11.5 23 1150)
     (250 "РУ-250" 18 35 1800)
     (300 "РУ-300" 26 51 2600)
     (400 "РУ-400" 45 90 4500)
     (500 "РУ-500" 71 141 7100)
     (600 "РУ-600" 102 204 10200)
     (700 "РУ-700" 140 277 14000)
     (800 "РУ-800" 180 362 18000)
     (900 "РУ-900" 230 458 23000)
     (1000 "РУ-1000" 285 565 28500)
     )
  )

;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
(defun SVTU|gendataRU (xlslinesF)
  (mapcar
    ;(setq xlsline (car xlslinesF))
    '(lambda (xlsline / DN)
       ;(setq DN (rtos* (cadr (assoc (atof* (xlsgpar "Diam_tr" xlsline)) (mapcar 'reverse #SVTU|Dy-DN)))))
       (setq DN (get-closer-from-row (atoi (xlsgpar "Dtr" xlsline)) (mapcar 'car #SVTU|RUlist)))
       (list
	 (strcat (xlsgpar "KKS" xlsline) "QB01")
	 DN
	 (xlsgpar "place_sensor" xlsline)
	 ))xlslinesF)
  );defun
;(SVTU|gendataRU xlslinesF)
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(setq lstRU (SVTU|gendataRU xlslinesF))
(defun gen-grafaRU (lstRU / out)
  (if (and (= 2 (length lstRU)) (= (cadar lstRU) (cadadr lstRU)))
    (setq out (list (list
	   (strcat "{\\W0.8;\\T0.85;" (car (car lstRU)) ",\n" (car (cadr lstRU)) "}")
	   (strcat "Участок расходомерный DN " (itoa (cadr (car lstRU))) "						2\\~шт." "\n" (caddr (car lstRU)))
	   (cadr (assoc (cadr (car lstRU)) #SVTU|RUlist))
	   ;(strcat "РУ-" (cadr (car lstRU)))
	   )))
    ;(setq x (car lstRU))
    (setq out (mapcar '(lambda (x)
			 ;(setq x (car lstRU))
        (list
	  (strcat "{\\W0.8;\\T0.85;" (car x) "}")
	  (strcat "Участок расходомерный DN " (itoa (cadr x)) "						1\\~шт." "\n" (caddr x))
	  (cadr (assoc (cadr x) #SVTU|RUlist))
	  )
			 )lstRU))
    );if
  ;(append lst(list "" "" "" "" "" "" "" "" ""))
  );defun
;(gen-grafaRU lstRU)
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;





;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;    ДАТЧИКИ    ;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(SVTU|getDFdiap xlsline)
;;;;;;;;;;;;;;;;;;;;;;;;;;;;;;;;;;;;;;;;;;;;;;;;;;;;;;;;;;;;;;;;;;;;;;;;;;;;;;;;;;;;;;;;;;;;;;;;


(defun SVTU|getDFdiap (xlsline / D fmin fmax lst actfmin actfmax)
  ;(setq xlsline (car xlslinesF))

  (setq D (atoi (xlsgpar "Dtr" xlsline)))
  (if (and D (member D (mapcar 'car (mapcar 'reverse #gost|Dy-Dn))))
    (setq D (cadr (assoc D (mapcar 'reverse #gost|Dy-Dn))))
    )


  (setq lst (assoc D #SVTU|RUlist))
    (setq fmin (nth 2 lst))
    (setq fmax (nth 4 lst))
    (setq actfmin (xlsgpar "min_val" xlsline))
    (setq actfmax (xlsgpar "max_val" xlsline))
    (if (or (null actfmin) (= "" actfmin) (= "#" actfmin)) (setq actfmin fmin) (setq actfmin (atof* actfmin)))
    (if (or (null actfmax) (= "" actfmax) (= "#" actfmax)) (setq actfmax fmax) (setq actfmax (atof* actfmax)))
    (if (and (>= actfmin fmin) (<= actfmax fmax)) (strcat (rtos* fmin) "..." (rtos* fmax) "\\~" (xlsgpar "units" xlsline))
      (progn (alert (strcat "\nне SVTU выбор диапазона\n не проходит данный диапазон расходов по диаметру\n" "позиция" (xlsgpar "KKS" xlsline)))
	(exit)))
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(SVTU|expandFdats xlslinesF)
(defun SVTU|expandFdats (xlslinesF / explines)
  (setq explines '())
  ;(setq xlsline (car xlslinesF))
  ;(SVTU|genqdat xlsline)

  
;;;;;;;;;;;;;;;;;;;;;;;;;;;;;;;;;;;;;;;;;;;;;;;;;;;;;;;;;;;;;;;;;;;;;;;;;;;;;;;;;;;;;;;;;;;;;;;;
  ;get quantity of Flow sensors
  (defun SVTU|genqdat (xlsline / D) ;(setq dN 80)
    (setq D (atoi (xlsgpar "Dtr" xlsline)))
    (if (and D (member D (mapcar 'car (mapcar 'reverse #gost|Dy-Dn))))
      (setq D (cadr (assoc D (mapcar 'reverse #gost|Dy-Dn))))
      )
    (cond
      ((diap D 32 150) 2)
      ((diap D 200 1000) 4)
      )
    );defun
;;;;;;;;;;;;;;;;;;;;;;;;;;;;;;;;;;;;;;;;;;;;;;;;;;;;;;;;;;;;;;;;;;;;;;;;;;;;;;;;;;;;;;;;;;;;;;;;

  
  (mapcar
    '(lambda (xlsline / qdat str i)
       (setq qdat (SVTU|genqdat xlsline))
       (setq i 64 str "")
       (repeat qdat
	 (setq  explines (append explines(list
		  (subst (strcat (xlsgpar "KKS" xlsline) (chr (setq i (1+ i)))) (xlsgpar "KKS" xlsline) xlsline))))
	 );repeat
       )xlslinesF)
  explines
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(SVTU|gendataFT xlslinesF)
(defun SVTU|gendataFT (xlslinesF)
  (ziplist (mapcar '(lambda (xlsline) (list (SVTU|getDFdiap xlsline) xlsline))
      (SVTU|expandFdats xlslinesF)))
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(gen-grafsdat xlslinesF)
(defun gen-grafsdat (lstFT)
  ;(setq lstFT (SVTU|gendataFT xlslinesF))
  (mapcar
    ;(setq xlslines (cadr (mapcar 'cdr lstFT)))
    '(lambda (xlslines)
       (list
	 (strcat "{\\W0.95;\\T0.9;" (spc|gsfxl "KKS" ",\n" xlslines)"}")
	 (strcat
	   "Датчик расхода ультразвуковой"
	   "						"
	   (rtos* (length xlslines))
	   "\\~шт.\n"
	   "с фторопластовым уплотнительным кольцом\n"
	   "Диапазон измерений: "
	   ;  (SVTU|getDFdiap (car xlslines))   -  если писать диапазон прибора
	   (db|gpar "min_val" (car xlslines)) "..." (db|gpar "max_val" (car xlslines)) " " (db|gpar "units" (car xlslines))
	   "\n" "По месту"
	   )
	 "ДР"
	 )
       )
    (mapcar 'cdr lstFT))
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;






;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;     Т С П     ;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;


;;; берем вариант только с гильзами
;;;  => тип бобышки - только 2
;;;    (1-ый без гильзы)



(setq
  #SVTU|gilzvars
   '(
     ;DN	Lзг	Lтсп  bobysh	anlge	типТС
     (32	nil	58	1	45	4)
     (50	56	58	5	60	4)
     (65	56	58	6	90	4)
     (80	56	58	6	90	4)
     (100	78.5	80	6	90	2)
     (125	78.5	80	6	90	2)
     (150	148	150	4	45	3)
     (200	148	150	5	60	3)
     (225	148	150	5	60	3)
     (250	148	150	5	60	3)
     (300	148	150	5	60	3)
     (400	148	150	5	60	3)
     (500	303	310	nil	90	5)
     (600	353	360	nil	90	6)
     ))


;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;; объединение по диаметрам
(defun SVTU|gendataTSP (xlslinesT)
  ;(ziplist (mapcar '(lambda (xlsline) (list (xlsgpar "Diam_tr" xlsline) xlsline)) xlslinesT))
  (cdr (db|mapzip (cons "table" xlslinesT) "Dtr"))
  );defun
;(SVTU|gendataTSP xlslinesT)
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;(setq lstTSP (SVTU|gendataTSP xlslinesT))
(defun gen-grafsTSP (lstTSP)
  (mapcar
    ;(setq xlslines (cdr (car lstTSP)))
    '(lambda (xlslines / D gilzaparams qtc typebobysh)
       (setq qtc (length xlslines))
       (setq D (atoi (xlsgpar "Dtr" (car xlslines))))
       (if (and D (member D (mapcar 'car (mapcar 'reverse #gost|Dy-Dn))))
	 (setq D (cadr (assoc D (mapcar 'reverse #gost|Dy-Dn))))
	 )
       (if (> D 600)
	 (setq gilzaparams (assoc 600 #SVTU|gilzvars))
	 (setq gilzaparams (assoc D #SVTU|gilzvars))
	 )
       
       (if (nth 1 gilzaparams)
	 (setq typebobysh "второго")
	 (setq typebobysh "первого")
	 )
       (list
	 (strcat "{\\W0.95;\\T0.9;" (spc|gsfxl "KKS" ", " xlslines) "}")
	 (strcat
	   "Термопреобразователь сопротивления Lтс=" (rtos* (nth 2 gilzaparams))
	   (if (nth 3 gilzaparams)
	     (strcat "; тип " (rtos* (nth 5 gilzaparams)) "			")
	     "				"
	     );if
	   (rtos* qtc) "\\~шт.\n"
	   
	   (if (nth 1 gilzaparams)
	     (strcat
	       "Защитная гильза Lзг=" (rtos* (nth 1 gilzaparams)) "							"
	       (rtos* qtc) "\\~шт.\n"
	       )
	     ""
	     )
	   "Втулка " typebobysh " типа, вариант " (rtos* (nth 3 gilzaparams)) "						"
	   (rtos* qtc) "\\~шт."
	   )
	 "ТСП-С"
	 )
       )
    (mapcar 'cdr lstTSP))
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
(defun gen-grafaothers ()
  (list
    (list "" "Встроенный блок расширения							1\\~шт." "РЕГ")
    (alert "проверить заказ СВТУ на наличие\nвстроенного блока регулятора или расширения \n как записывается")
;;;    (list ""
;;;      (strcat
;;;	"Щиток приборный, в комплекте:						" "1\\~шт.\n"
;;;	"коробка клеммная, розетка трехполюсная, автомат безопасности"
;;;	)
;;;      )
    )
  );defun
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;


;(VL-STRING->LIST (vla-get-TextString (vlax-ename->vla-object (car (entsel)))))

;;;  (spc|gsfxl3
;;;    '("meas_name" "P" "T" "nom_val" "units")
;;;    (list " " (if (> 10 (atof* p)) "МПа, " "кПа, ")        )
;;;    xlslinesF)


  (defun SVTU|gen-paragraph-name (xlslinesF)
    (strcat "{\\W0.9;\\T0.95;"
    (vl-string-right-trim "\n"  (apply 'strcat
	(mapcar
	   ;(setq xlsline (car xlslinesF))
	   '(lambda (xlsline / p)
	      (strcat
		(xlsgpar "meas_name" xlsline) " "
		(setq p (xlsgpar "P" xlsline)) "\\~"
		(if (> 10 (atof* p)) "МПа, " "кПа, ")	;;; если цифра больше 10 - то это кПа если нет - то МПа
		(xlsgpar "T" xlsline) "\\~%%dC, "
		(xlsgpar "nom_val" xlsline) "\\~"
		(xlsgpar "units" xlsline) "\n"
		)
	      )
	   xlslinesF)
	 )
       )
	   "}" )
    );defun


;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;

;(setq kompldata (nth 0 datazipped))
;(setq kompldata (nth 5 datazipped))
(defun gen-zakaz-SVTU
       (kompldata	;komlekt data
	/
	xlslines
	xlslinesF
	xlslinesT
	qkompl			;komplekt quantity
	pogresh			; погрешность - М1 или М2 - пока не буду писать табл. 3.1
	varisp			; модификация прибора табл. 3.1

	strnames
	strSVTUzakaz
	
	strVychkks
	outlist
	)

  ; модификация = погрешность
  (setq pogresh "М1")
  ;(setq pogresh "")
  ;; в наших проектах с нашими теплосетями вариант исполнения всегда 3
  (setq varisp "3")
  (setq strVychkks (car kompldata))
  (setq xlslines (cdr kompldata))
  (setq qkompl 1)
  ;;; эту переменную мы будем дополнять в процессе генерации данных
    
  (setq xlslinesF (vl-remove-if-not '(lambda (x) (= "FT" (xlsgpar "Fkip" x))) xlslines))
  (setq xlslinesT (vl-remove-if-not '(lambda (x) (= "TTF" (xlsgpar "Fkip" x))) xlslines))



  (setq strSVTUzakaz
     (strcat
       "{\\W0.9;"
       "СВТУ10М"
       "-"
       pogresh
       "-"
       varisp
       "-\n-"
       ;; расходомерные устройства
       (vl-string-right-trim "/" (apply 'strcat
        (mapcar '(lambda (x / d)
		   ;(setq x (car (SVTU|gendataRU xlslinesF)))
		   (setq d (cadr x))
		   (strcat
		     "РУ"
		     (vl-string-left-trim "РУ-" (cadr (assoc d #SVTU|RUlist)))
		     (if (>= d 200) "ф" "")
		     "(#LкабF#)"
		     "/")
		   )
		(SVTU|gendataRU xlslinesF))))
       "-\n-"
       (vl-string-right-trim "/" (apply 'strcat
	 (mapcar '(lambda (xlsline / D gilzaparams)
		    ;(setq xlsline (cadr  xlslinesT))
		    (setq D (atoi (xlsgpar "Dtr" xlsline)))
		    (if (and D (member D (mapcar 'car (mapcar 'reverse #gost|Dy-Dn))))
		      (setq D (cadr (assoc D (mapcar 'reverse #gost|Dy-Dn))))
		      )
		    (if (> D 600)
		      (setq gilzaparams (assoc 600 #SVTU|gilzvars))
		      (setq gilzaparams (assoc D #SVTU|gilzvars))
		      )
		    ;(setq gilzaparams (assoc D #SVTU|gilzvars))
		    (strcat
		      (rtos* (nth 5 gilzaparams))       ;; тип ТСП в зависимости от диаметра
		      "в"
		      (rtos* (nth 4 gilzaparams))	;; угол взавис от диам
		      "г"				;; наличие гильзы
		      "(#LкабT#)"
		      "/")
		    )
		 xlslinesT)))
       "-\n"
       ;"Д1(30)/Д2(15)-"				;; надичиче датчиков давления (метры)
       ;"USB(2)-"					;; наличие интерфейса
       ;"Л(3)-"						;; наличие линейных выходов (м)
       ;"Л(2)-"						;; наличие линейных выходов (м)
       "Л(1)-"						;; наличие линейных выходов (м)
       ;"К(3)-"						;; наличие ключевых выходов (м) (дискретные для управления)
       ;"И(5)-"						;; наличие импульсных выходов (м)
       ;"Ивх(5)-"					;; наличие импульсных входов (м)
       "220\n"
       "ТУ РБ 191182855.001-2011"
       "}"
       ))




  
  
  (append
    (list
      (list "" (SVTU|gen-paragraph-name xlslinesF) "" "" "" "" "" "" "")
      (list "" "Тепловодосчетчик" strSVTUzakaz "" "ООО \"КИПпромэнерго\"\nг. Минск" "Компл." qkompl "" "Аналог")
      (list "" "В состав комплекта входит:" "" "" "" "" "" "" "")
      (list strVychkks (strcat "Вычислитель с блоком расширения						1\\~шт.\nВыходной сигнал 4...20 мА, питание ~220 В, 50 Гц\n"
			       (xlsgpar "place_cpu" (car xlslinesF))) (strcat "СВТУ10М" "-" pogresh "-" varisp) "" "" "" "" "" "")
      (list "" "" "" "" "" "" "" "" "")
      )
    (gen-grafaRU (SVTU|gendataRU xlslinesF))
    (list (list "" "" "" "" "" "" "" "" ""))
    (gen-grafsdat (SVTU|gendataFT xlslinesF))
    (list (list "" "" "" "" "" "" "" "" ""))
    (gen-grafsTSP (SVTU|gendataTSP xlslinesT))
    (list (list "" "" "" "" "" "" "" "" ""))
    (gen-grafaothers)	; если есть выход в контроллер
    (list
      (list "" "" "" "" "" "" "" "" "")
      (list "" "" "" "" "" "" "" "" "")
      )
    )
  );defun


;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;
