;(setq xlslines (cdr (nth 1 datazipped)))
;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;

(if (null sepstr) (load (strcat #lisppath "strings\\stringlib.lsp")))

(setq
  #diafr:ost108.839.02-82
   '(
     ("01" 50 )
     ("02" 80)
     ("03" 150)
     ("04" 200)
     ("05" 250)
     ("06" 300)
     ("07" 100)
     ("08" 100)
     ("09" 100)
     ("10" 300)
     ("11" 350)
     ("12" 400)
     ("13" 450)
     )
   )


;ГОСТ 8.586-2005   7 34.10.756-97



(defun gen-zakaz-diafragma (xlslines / typ sign spec)
  (setq typ (sepstr (xlsgpar "sampling_device" (car xlslines)) " "))
  (setq spec (xlsgpar "special" (car xlslines)))
  (setq spec (mapcar '(lambda (x) (sepstr x "=")) (sepstr spec ";")))

  (setq
    sign
     (cond
       ((= "108.839.02-82" (caddr typ))
	(list
	  (strcat "Блок с диафрагмой исполнения " (car typ) " с условным проходом Dу\\~=\\~" (rtos* (cadr (assoc (car typ) #diafr:ost108.839.02-82))))
	  (strcat (xlsgpar "sampling_device" (car xlslines)) "\n" "Опросный лист " (cadr (assoc "Noprlist" spec)))
	  )
	)
       ;;;;;;;;;;;;;;;;
       (T (exit))
      );cond
    )


  (append
    (list (strcat "{\\W0.8;\\T0.8;" (xlsgpar "KKS" (car xlslines)) "QP01" "}" ))
    sign
    (list "" "" "шт." "1" "" "")
    )
     
;;;  (list
;;;    ""
;;;    (strcat "Диарагма камерная по ГОСТ 8.586.(1-5)-2005\nдля установки во фланцевом соединении по "
;;;	    (xlsgpar "sampling_device" xlsline))
;;;    (strcat "ДКС-#######" "\n"
;;;	    "Опросный лист #####")
;;;    "" "" "шт." (rtos* kol) "" "")
  );defun
;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;





;;;Блок с диафрагмой исполнения 02 с условным проходом Dу = 80по 02 ОСТ 108.839.02-82
;;;02 ОСТ 108.839.02-82
;;;Опросный лист 01 04 08
