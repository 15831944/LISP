;13_11_06
;(setq xlslines (cdr (nth 1 datazipped)))

(defun pointmnt|gen-zakaz-sosudur (xlslines / quant mater typ)
  (setq quant (length xlslines))
  
  (if (= "dPTF" (xlsgpar "func" (car xlslines))) (setq quant (* 2 quant)))

  (setq mater "А")	;;; Сталь 20
  ;(setq mater "Б")	;;; 12Х18Н10Т
  ;(setq mater "В")	;;; марка стали заказчика
  ;;; принятый тип сосуда
  (setq typ "СУ-10-01-А")
  (if (< (* 1.2 (atof* (xlsgpar "P" (car xlslines)))) 10)
    (list "" "Сосуд уравнительный" typ "" "ООО \"ПОИНТ\" г. Полоцк" "шт." (rtos* quant) "" "Аналог")
    (list "" "!!! ###  ПРИНЯТЫЙ ТИП СОСУДА НЕ ПОДХОДИТ  ### !!!" "" "" "" "" "" "" "")
    )
  );defun





;;;;;   пример описания таблыци выбора сосуда уравненительного ПОИНТ

;;;
;;;'(
;;;  	(10
;;;   		(01
;;;    			("НСН"
;;;     				("Ст20" "СУ-10-01-А (НСН-14-М20x1,5)")
;;;     				("12Х" "СУ-10-01-Б (НСН-14-М20x1,5)")
;;;    			)
;;;   		)
;;;   		(02
;;;    			("К1/2"
;;;     				("Ст20" "СУ-10-02-А (К1/2)")
;;;     				("12Х" "СУ-10-02-Б (К1/2)")
;;;    			)
;;;    			("Rc1/2"
;;;     				("Ст20" "СУ-10-02-А (Rc1/2)")
;;;     				("12Х" "СУ-10-02-Б (Rc1/2)")
;;;    			)
;;;   		)
;;;  	)
;;;  	(25
;;;   		(02
;;;    			("К1/2"
;;;     				("Ст20" "СУ-25-02-А (К1/2)")
;;;     				("12Х" "СУ-25-02-Б (К1/2)")
;;;    			)
;;;    			("Rc1/2"
;;;     				("Ст20" "СУ-25-02-А (Rc1/2)")
;;;     				("12Х" "СУ-25-02-Б (Rc1/2)")
;;;    			)
;;;   		)
;;;  	)
;;; )
