; 13_12_28
; WIKA




;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun wika|*gen*zakaz (xlslines / $xlsline $D_korpus $mnttype $Lbobysh $procconnect $Dshtok $Tdiap)
  ;(setq xlslines xlslinesTT)
  (setq $xlsline (car xlslines))
  (setq $D_korpus 100)
  (setq $mnttype "S")
  (setq $procconnect "G1/2B")
  (setq $Dshtok 8)
  (setq $Lbobysh (wika|*get*Lbobysh $xlsline))
  (setq $Lmont (wika|*get*Lmont $xlsline))
  (setq $Lgilza (wika|*get*Lgilza $xlsline))
  (setq $Tdiap (wika|*get*Tdiap $xlsline))
  
  (append
    (wika|*gen*zakaz-dat xlslines)		;;;; (("" "" ""))
    ;'((""))
    (wika|*gen*zakaz-gilza xlslines)
    ;'((""))
    ;(wika|*gen*zakaz-bobyshka xlslines)
    (wika|*gen*zakaz-bobyshka-POINT xlslines)		;; поинтовская бобышка
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;





;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;(setq xls-head '("S" "Sконтур" "ветка" "среда" "func" "PID" "sign_type" "min_val" "nom_val" "max_val" "units" "T" "P" "F" "прототип" "Diam_tr" "scale" "place_sensor" "meas_name" "KKS" "рег" "power" "cpu" "place_cpu" nil "special" "remarks" "sampling_device"))
;(setq xlsline '("" "20" "" "СВРК3" "TE" "TEC" "ТСП" "" "70" "" "%%dС" "" "" "" "ТС-Б" "426" "" "По месту" "Температура сетевой воды РК-3 на выходе из РК-1" "RDT002" "RD201" "ТСП" "RDC001" "ЦТЩ" "" "" "" ""))
(defun wika|*get*Tdiap (xlsline / #wika:Trange valnom valmax valsafe scval)
  (setq #wika:Trange '(60 80 100 120 160 200 250 300 400 500))
  (setq valnom (atof* (xlsgpar "nom_val" xlsline)))
  (setq valmax (atof* (xlsgpar "max_val" xlsline)))
  (setq valsafe (max (* 1.2 valnom) (* 1.2 valmax)))
  (setq scval (apply 'min (vl-remove-if '(lambda (x) (<= (- x valsafe) 0)) #wika:Trange)))
  (list 0 scval)
  )
;(wika|*get*Tdiap xlsline)
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;



;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun wika|*get*Lbobysh (xlsline / Dn OT)
  ; договоренность про бобышки для вики - это если заказываем сами 40
  ; если бобышка ОТ-шная то по госту 01 ОСТ 108.530.01 их длина 80
  (setq OT (xlsgpar "sampling_device" xlsline))
  (cond
    ((and OT (/= OT "") (= OT "01 ОСТ 108.530.01")) 80)
    ((or (null OT) (= OT ""))
     (setq Dn (atof* (xlsgpar "Diam_tr" xlsline)))
     ;(cond ((< Dn 150) 40) ((>= Dn 150) 80))
     40
     )
    (T (princ "\nНЕ распознан тип бобышки") (exit))
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;(setq xlsline (car xlslines))
(defun wika|*get*Lmont (xlsline / #wika|Lmch-cat Lb Dn Lsafe)
  (setq #wika|Lmch-cat '(63 100 160 200 250))
  (setq Lb (wika|*get*lbobysh xlsline))
  (setq Dn (atof* (xlsgpar "Diam_tr" xlsline)))
  (setq Lsafe (+ (* 0.45 Dn) Lb 28))
  (get-closer-from-row Lsafe #wika|Lmch-cat)
  );defun
;(wika|*get*Lmont xlsline)
;;;;;;;;;;;;;;;;;;;;;;;;;;;;;;;;;;;;;;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun wika|*get*Lgilza (xlsline)
  ; будем использовать гильзу с внутренней резббой - SD600G
  ; с резьбой G1/2  
  (- (wika|*get*Lmont xlsline) 18)
  )
;(wika|*get*Lgilza xlsline)
;;;;;;;;;;;;;;;;;;;;;;;;;;;;;;;;;;;;;;;;;;;;;;;;;;;;;;;;;;;;;;;;;;;;;;;;;;;;;;;;;;;;;;;;;;;;;;;;;;;;;;;;;;;;;;;;;;;;;







;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;(setq xlslines xlslinesTT)
(defun wika|*gen*zakaz-dat (xlslines / quant pozitions)
  (setq pozitions (VL-STRING-RIGHT-TRIM ", " (eval (append (list 'strcat) (mapcar '(lambda (line)(strcat(xlsgpar "KKS" line) ", "))xlslines)))))
  (setq quant (length xlslines))
  (list
    (list
      ;(strcat "{\\W0.8;\\T0.9;" pozitions "}" )
      pozitions
      (strcat
	"Термометр биметаллический показывающий, номинальный размер " (rtos* $D_korpus) "\n"
	"диапазон измерений " (rtos* (car $Tdiap)) "..." (rtos* (cadr $Tdiap)) "\\~%%dC" ", присоединение " $procconnect "\n"
	"длина штока " (rtos* $Lmont) ", распололжение радиальное" "\n"
	"тип подключения - " $mnttype ", " "диаметр штока " (rtos* $Dshtok) ;"\n"
	;"Трубопровод"
	)
      (strcat "R52." (rtos* $D_korpus) "\nТМ52.01")
      ""
      (strcat "Фирма\\~\"WIKA\"\nЗАО\\~\"Линтера\" г.\\~Минск")
      "шт." (rtos* quant) "" "Аналог"
      )
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;



;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun wika|*gen*zakaz-gilza (xlslines /  kol)
  (setq kol (length xlslines))
  (list
    (list
      ""
      (strcat
	"Гильза защитная. Длина монтажной части " (itoa $Lgilza) " мм" "\n"
	"Внешяя резьба G1/2B, внутренняя резьба G1/2"
	)
      (strcat "SD600G")
      ""
      (strcat "Фирма\\~\"WIKA\"\nЗАО\\~\"Линтера\" г.\\~Минск")
      "шт." (rtos* kol) "" "Аналог"
      )
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;



;     1!!!!!!!!!!!!   по хорошему длину бобышки надо выбирать по изоляции трубы
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun wika|*gen*zakaz-bobyshka (xlslines /  kol)
  (setq kol (length xlslines))
  (list
    (list
      ""
      "Бобышка G1/2"
      "БТБ"
      ""
      (strcat "{\\W0.95;\\T0.9;" "СО \"Завод теплотехнических приборов\" г.\\~Минск" "}")
      "шт." (rtos* kol) "" "Аналог"
      )
    )
  );defun




;(setq xlslines (cdr (nth 1 datazipped)))
(defun wika|*gen*zakaz-bobyshka-POINT (xlslines / rezba kol  Lbob)
  (setq kol (length xlslines))
  (setq rezba "G1/2")
  (setq Lbob 40) ;- с такой резьбой G1/2 - только 40
  (list
    (list
      ""
      (strcat "Бобышка: L=" (rtos* Lbob) " мм, присоединение " rezba ", Ст.20")
      (strcat "1/28-" (rtos* Lbob) "-" rezba)
      "" "ООО \"ПОИНТ\" г. Полоцк"  "шт." (rtos* kol) "" "Аналог"
      )
    )
  );defun


;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
