; 13_05_29
; 13_11_05
; ТП-Б ПШ (Полоцк, "ПОИНТ")
; ступенчатый чехол
; погружаемый
; ПШ
; клеммная головка E
(setq #point|headtype "Е")

;;;; договорились брать все гильзы - цилиндрические цельноточенные резьбовые, из нерж. стали
;;;; на давление 25 МПа (то есть диаметр 16)
;;;; в установка параметров - ф самой функции генерации заказа




;;;;;;;;;;;;;;;;;;;;;;;;;;;;;;;;;;;;;;;;;;;;;;;;;;;;;;;;;;;;;;;;;;;;;;;;;;;;;;;;;;;;;;;;;;
;(setq xlsline (car xlslines))
;(setq xlsline (car (DB|FORMATDATA(excel>lst))))
(defun getlbobysh (xlsline / Dn OT)
  ; договоренность про бобышки - это если заказываем сами 40 или 80 мм - в зависимости от диаметра
  ; если бобышка ОТ-шная то по госту 01 ОСТ 108.530.01 их длина 80
  (setq OT (xlsgpar "sampling_device" xlsline))
  (cond
    ((and OT (/= OT "") (= OT "01 ОСТ 108.530.01")) 80)
    ((or (null OT) (= OT "")) (setq Dn (atof* (xlsgpar "Diam_tr" xlsline)))(cond ((< Dn 150) 40) ((>= Dn 150) 80)))
    (T (princ "\nНЕ распознан тип бобышки") (exit))
    )
  );defun
;(getlbobysh xlsline)

;(setq xlsline (nth 14 data))
(defun point-TP|getrange (xlsline / valsafe valnom valmax scval #point-TP|catrangesT)
  (setq #point-TP|catrangesT '(600 700 800 900))
  (setq valnom (atof* (xlsgpar "nom_val" xlsline)))
  (setq valmax (atof* (xlsgpar "max_val" xlsline)))
  (setq valsafe (max (* 1.2 valnom) (* 1.2 valmax)))
  (setq scval (apply 'min (vl-remove-if '(lambda (x) (<= (- x valsafe) 0)) #point-TP|catrangesT)))
  (list 0 scval)
  );defun
;(point-TP|getrange xlsline)
;;;;;;;;;;;;;;;;;;;;;;;;;;;;;;;;;;;;;;;;;;;;;;;;;;;;;;;;;;;;;;;;;;;;;;;;;;;;;;;;;;;;;;;;;;


(defun point-TP|getLmont (xlsline / Dn Lb Lmin Lmax #point-TP|catrangesLmch  Lsafe) 
  (setq #point-TP|catrangesLmch '(120 160 200 250 320 400 500 630 800 1000 1600 2000 2500 3150))
  (setq Lb (getlbobysh xlsline))		;длина бобышки
  (setq Dn (atof* (xlsgpar "Diam_tr" xlsline)))
  (setq Lsafe (+ (* 0.37 Dn) Lb))
  (apply 'min (vl-remove-if '(lambda (x) (<= (- x Lsafe) 0)) #point-TP|catrangesLmch))
  );defun
;(point-TP|getLmont xlsline)



;;;;;;;;;;;;;;;;;;;;;;;;;;;;;;;;;;;;;;;;;;;;;;;;;;;;;;;;;;;;;;;;;;;;;;;;;;;;;;;;;;;;;;;;;;

(defun point-TP|getLnar (xlsline / Tmax)
  (setq Tmax (* 1.1 (cadr (point-TP|getrange xlsline))))
  (cond
    ((diap Tmax -100 399) 50)
    ((diap Tmax 0    799) 120)
    ((diap Tmax 800 1000) 160)
    ((> Tmax        1000) 200)
    )
  );defun
;(point-TP|getLnar xlsline)
;;;;;;;;;;;;;;;;;;;;;;;;;;;;;;;;;;;;;;;;;;;;;;;;;;;;;;;;;;;;;;;;;;;;;;;;;;;;;;;;;;;;;;;;;;
;;;  (defun point|get-diam-mch ( / tmp)
;;;    (setq tmp (* L_mch 1.1))
;;;    (cond
;;;      ;((diap tmp 0 320) 6)
;;;      ((diap tmp 0 1000) 8)
;;;      (T 10)
;;;      )
;;;    );defun
;;;;;;;;;;;;;;;;;;;;;;;;;;;;;;;;;;;;;;;;;;;;;;;;;;;;;;;;;;;;;;;;;;;;;;;;;;;;;;;;;;;;;;;;;;






;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;1
;(setq xlslines (cdr (nth 2 datazipped)))
;(setq xlslines data)
(defun gen-zakaz-point-TP (xlslines)
  (append
    (point-TP|gen-zakaz-dat xlslines)		;;;; (("" "" ""))
    (point|gen-zakaz-gilza xlslines)
    (point|gen-zakaz-bobyshka xlslines)
    (point|gen-zakaz-rasshiritel xlslines)
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;





;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;(setq xlslines xlslinesTT)
(defun point-TP|gen-zakaz-dat (xlslines /
			       Dschup Dmont
			       kol range
			       Lmont Lnar
			       spytype
			       pozitions
			       )
  (setq spytype "И")	;;;; тип спая по каталогу
  ; у ступенчатых чехлов других вариантов тут нет
  (setq pozitions (VL-STRING-RIGHT-TRIM ", " (eval (append (list 'strcat) (mapcar '(lambda (line)(strcat(xlsgpar "KKS" line) ", "))xlslines)))))
  (setq Dschup 8)
  (setq Dmont 10)
  (setq kol (length xlslines))
  (setq range (point-TP|getrange (car xlslines)))
  (setq Lmont (point-TP|getLmont (car xlslines)))
  (setq Lnar (point-TP|getLnar (car xlslines)))

  (list
    (list
      (strcat "{\\W0.8;\\T0.9;" pozitions "}" )
      (strcat
	"Преобразователь термоэлектрический унифицированный погружной:" "\n"
	"класс точности 0,5 %, диапазон измерения (" (rtos* (car range)) "...+" (rtos* (cadr range)) ") °C," "\n"
	"длина монтажной части " (rtos* Lmont) " мм, диаметр монтажной части " (rtos* Dmont) " мм," "\n"
	"тип крепления - подвижный штуцер, длина наружной части " (rtos* Lnar) " мм," "\n"
	"присоединение M20x1,5, напряжение питания 24 В, степень защиты IP65;" "\n"
	"в комплекте:"
	)
      (strcat
	"ТП-Б-У (4-20)мА-(±0,5)-" spytype "-П-" "\n"
	;;;;;;;;;;;;;;;;;;;;;;;;;;;;;;;;;;;;;;;;;;;;;;;;;;;;;;;;;;;
	;;;;;;;;;;;;;;;;;;;;;;;;;;;;;;;;;;;;;;;;;;;;;;;;;;;;;;;;;;;
	"-(" (rtos* (car range)) "..." (rtos* (cadr range)) ")-" (rtos* Lmont) "/" (rtos* Dmont)
	"-ПШ." (rtos* Lnar) ".М20х1,5-" #point|headtype "\n"
	"ТУ РБ 390184271.012-2008"
	)
      ""
      (strcat "ООО \"ПОИНТ\"" " " "г. Полоцк")
      "шт." (rtos* kol) "" "Аналог"
      )
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun point|gen-zakaz-gilza (xlslines / kol Dnar Lmont)
  ;;;; цельноточеная - ГЦР.111
  (setq gtype "ГЦР.111")
  (setq kol (length xlslines))
  (setq Dnar 16)
  (setq Lmont (point-TP|getLmont (car xlslines)))

  (list
    (list
      ""
      (strcat
	"Гильза цилиндрическая резьбовая "
	(cond
	  ((member gtype '("ГЦР.111" "ГЦР.112" "ГЦР.121" "ГЦР.131")) "цельноточеная")
	  (T "сварная")
	  ) ":\n"
	"внешний диаметр " (rtos* Dnar) " мм, длина монтажной части " (rtos* Lmont) " мм," "\n"
	"присоединение M20x1,5, условное давление 25\\~МПа, материал\\~12Х18Н10Т;"
	)
      (strcat gtype "-M20x1,5-" (rtos* Dnar) "-"(rtos* Lmont)"-25")
      ""
      (strcat "ООО \"ПОИНТ\"" " " "г. Полоцк")
      "шт." (rtos* kol) "" "Аналог"
      )
    )
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
(defun point|gen-zakaz-bobyshka (xlslines / tmpr sreda sd kol Dnar Lbob)
  (setq kol (length xlslines))
  (setq tmpr (atof* (xlsgpar "nom_val" (car xlslines))))
  (setq
    sreda
     (cond
       ((>= tmpr 200) "пар")
       ((< tmpr 200) "вода")
       )
    )
  (setq sd (xlsgpar "sampling_device" (car xlslines)))
  (cond
    ((= sd "01 ОСТ 108.530.01")		;; 13_11_05
     (list
       (list
	 "" "Бобышка: L=80 мм, присоединение М20х1,5" "01 ОСТ 108.530.01" "" "" "шт." (rtos* kol) ""
	 (strcat
	   "Заказ по спецификации "
	   (cond
	     ((= sreda "пар") "1744-1-ТМ2")
	     ((= sreda "вода") "1744-1-ТМ3")
	     )
	   )
	 )
       )
     )
    ((null sd)
     (progn
       (setq Lbob (getlbobysh (car xlslines)))
       (list
	 (list
	   ""
	   (strcat "Бобышка: L=" (rtos* Lbob) " мм, присоединение M20x1,5")
	   (strcat "1/28-" (rtos* Lbob) "-M20x1,5")
	   ""
	   "ООО \"ПОИНТ\" г. Полоцк"
	   "шт." (rtos* kol) "" "Аналог"
	   )
	 )
       )
     )
    );cond чей заказ бобышки
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;; 13_11_05
;;;;;;;;;;;;;;;;;;;;;;;;;;;;;;;;;;;;;;;;;;;;;;;;;;;;;;;;;;;;;;;;;;;;;;;;;;;;;;;;;;;;;;;;;;;;;;;;;;;;;;;;;;;;;;;;;;;;;
(defun point|gen-zakaz-rasshiritel (xlslines / Dn kol typ)
  (setq Dn (atof* (xlsgpar "Diam_tr" (car xlslines))))
  (if (< Dn 40)
    (progn
      (setq kol (length xlslines))
      (setq typ (get-closer-from-row Dn '(25 32 38)))
      (list
	(list
	  ""
	  "Расширитель прямой с бобышкой, для установки приборов, 12Х18Н10Т"
	  (strcat "57x" (rtos* typ) "-M20x1,5-Б")
	  ""
	  "ООО \"ПОИНТ\" г. Полоцк" "шт." (rtos* kol) "" ""
	  )
	)
      )
    );if
  );defun
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;
