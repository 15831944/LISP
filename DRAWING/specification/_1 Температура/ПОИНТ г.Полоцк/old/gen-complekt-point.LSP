; 13_05_02
; ТС-Б ПШ (Полоцк, "ПОИНТ")
; ступенчатый чехол
; погружаемый
; ПШ

; генерация списка - части параграфа спецификации



;;;;;;;;;;;;;;;;;;;;;;;;;;;;;;;;;;;;;;;;;;;;;;;;;;;;;;;
;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;
(defun point|get-L_bobysh (/)
  (cond
    ((< D_truby 150) 40)
    ((>= D_truby 150) 80)
    )
  );defun
;;;;;;;;;;;;;;;;;;;;;;;;;;;;;;;;;;;;;;;;;;;;;;;;;;;;;;;;;;;;;;;;;;;;;;;;;;;;;;;;;;;;;;;;;;
;;;(defun point|get-tempr-scale (/ lst)
;;;  (cond
;;;    ((= sensor-type "ТП-Б-У-Е") (setq lst '(600 700 800 900)))
;;;    ((= sensor-type "ТС-Б-У-Е") (setq lst '(50 80 100 150 180 200 250 300 400 500)))
;;;    );defun
;;;  (get-closer-from-row CT_ lst)
;;;  );defun
;;;;;;;;;;;;;;;;;;;;;;;;;;;;;;;;;;;;;;;;;;;;;;;;;;;;;;;;;;;;;;;;;;;;;;;;;;;;;;;;;;;;;;;;;;
(defun point|get-tempr-scale* (CT styp / lstparams)
  (cond
    ((= styp "ТП-Б-У") (setq lstparams '(600 700 800 900)))
    ((= styp "ТС-Б-У") (setq lstparams '(50 80 100 150 180 200 250 300 400 500)))
    );defun
  (if lstparams
    (get-closer-from-row CT lstparams)
    0
    )
  );defun
;;;;;;;;;;;;;;;;;;;;;;;;;;;;;;;;;;;;;;;;;;;;;;;;;;;;;;;;;;;;;;;;;;;;;;;;;;;;;;;;;;;;;;;;;;
(defun point|getrange (xlsline / styp #point|catranges)
  (setq styp ())
  (cond
    ((= styp "ТП-Б-У") (setq #point|catranges '(600 700 800 900)))
    ((= styp "ТС-Б-У") (setq #point|catranges '(50 80 100 150 180 200 250 300 400 500)))
    );defun
  (if lstparams
    (get-closer-from-row CT lstparams)
    0
    )
  );defun
;;;;;;;;;;;;;;;;;;;;;;;;;;;;;;;;;;;;;;;;;;;;;;;;;;;;;;;;;;;;;;;;;;;;;;;;;;;;;;;;;;;;;;;;;;


(defun point|get-nearest-L_mont (/ lst condidatelist Lmch_min Lmch_max)
    (setq Lmch_min (+ (/ D_truby 3.0) L_bobysh))
    (setq Lmch_max (+ (/ D_truby 1.8) L_bobysh))
    (cond
      ((= sensor-type "ТП-Б-У-Е") (setq lst '(120 160 200 250 320 400 500 630 800 1000 1600 2000 2500 3150)))
      ((= sensor-type "ТС-Б-У-Е") (setq lst '(80 100 120 160 200 250 320 400 500 630 800 1000 1250 1600 2000 2500 3150)))
      )
    (setq condidatelist
	 (vl-remove-if
	   '(lambda (x)
	      (or
		(< x Lmch_min)
		(> x Lmch_max)
		)) lst))
    (if condidatelist
      (eval (append '(min) condidatelist))
      (eval (append '(min) lst))	;временная мера изза гребаных технологов с трубой 57 на 400 градусах
;;;      (if (< D_truby (- (car lst)  L_bobysh))
;;;	(alert "слишком тонкая труба и короткая бобышка\nнет такой длины монтажной части")
;;;	(car lst)
;;;	)
      )
  );defun
;;;;;;;;;;;;;;;;;;;;;;;;;;;;;;;;;;;;;;;;;;;;;;;;;;;;;;;;;;;;;;;;;;;;;;;;;;;;;;;;;;;;;;;;;;
(defun point|get-nearest-L_nar ( / tmp)
    (setq tmp (* T_diap 1.1))
    (cond
      ((diap tmp -100 399) 50)
      ((diap tmp 0    799) 120)
      ((diap tmp 800 1000) 160)
      ((> tmp        1000) 200)
      )
    );defun
;;;;;;;;;;;;;;;;;;;;;;;;;;;;;;;;;;;;;;;;;;;;;;;;;;;;;;;;;;;;;;;;;;;;;;;;;;;;;;;;;;;;;;;;;;
;;;  (defun point|get-diam-mch ( / tmp)
;;;    (setq tmp (* L_mch 1.1))
;;;    (cond
;;;      ;((diap tmp 0 320) 6)
;;;      ((diap tmp 0 1000) 8)
;;;      (T 10)
;;;      )
;;;    );defun
;;;;;;;;;;;;;;;;;;;;;;;;;;;;;;;;;;;;;;;;;;;;;;;;;;;;;;;;;;;;;;;;;;;;;;;;;;;;;;;;;;;;;;;;;;






;;;
;;;
;;;
;;;
;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;
;;;(defun gen-complekt-point (xlsline /
;;;			   CP_ CT_ D_truby
;;;			   bobyshka-OT L_bobysh
;;;			   sensor-type T_diap L_mch L_nch diam_schup diam_mch
;;;			   paragraph kol
;;;			   )
;;;
;;;  ;;;;;;;;;;;;;;;;;;;;;;;;;;;;;;;;;;;;;;;;;;;;;;;;;;;;;;;;;;;;;;;;;;;
;;;  ;;;;;;;;;;;;;;  выбор параметров комплекта датчика  ;;;;;;;;;;;;;;;
;;;  ;;;;;;;;;;;;;;;;;;;;;;;;;;;;;;;;;;;;;;;;;;;;;;;;;;;;;;;;;;;;;;;;;;;
;;;  ; CP_ МПа
;;;  (if (and
;;;	(setq CP_ (xlsgpar "P" xlsline))
;;;	(isnumericstring CP_)
;;;	)
;;;    (setq CP_ (atof* CP_))
;;;    (setq CP_ 0.1)
;;;    )
;;;  
;;;  (setq CT_ (max (* 1.6 (atof* (xlsgpar "nom_val" xlsline))) (* 1.2 (atof (xlsgpar "max_val" xlsline)))))
;;;  (setq D_truby (atoi (xlsgpar "Diam_tr" xlsline)))
;;;  (setq kol 1)
;;;  ;;;;;;;;;;;;;;;;;;;;;;;;;;;;;;;;;;;;;;;;;;;;;;;;;;;;;;;;;;;;;;;;;;;
;;;  ;;;;;;;;;;;;;;;;;;;;;;;;;;;;;;;;;;;;;;;;;;;;;;;;;;;;;;;;;;;;;;;;;;;
;;;
;;;  ;;;; толщина изоляци
;;;  ;(load (strcat #lisppath "specification\\толщина изоляции.LSP")) ; ТКП45-4.02-129-2009 = list
;;;  ;(setq dL_izo (get-closer-from-table CT_ D_truby #ТКП45-4.02-129-2009))
;;;  ;;;;;;;;;;;;;;;;;;;;;;;;;;;;;;;;;;;;;;;;;;;;;;;;;;;;;;;;;;;;;;;;;;;;;;;;;;;;;;;;;;;;;;;;;;;;
;;;  ;;;     по хорошему нужно учитывать для выбора составляющих
;;;  ;;;;;;;;;;;;;;;;;;;;;;;;;;;;;;;;;;;;;;;;;;;;;;;;;;;;;;;;;;;;;;;;;;;
;;;
;;;
;;;  ;;;;;;;;;;;;;;;;;;;;;;;;;;;;;;;;;;;;;;;;;;;;;;;;;;;;;;;;;;;;;;;;;;;
;;;  ;;;;;;;;;;;;;;;;;     БОБЫШКА     ;;;;;;;;;;;;;;;;;;;;;;;;;;;;;;;;;
;;;  ;;;;;;;;;;;;;;;;;;;;;;;;;;;;;;;;;;;;;;;;;;;;;;;;;;;;;;;;;;;;;;;;;;;
;;;  
;;;  (setq bobyshka-OT (or (> CP_ 2.6) (= "ОТ" (xlsgpar "sampling_device" xlsline))))
;;;  
;;;	
;;;
;;;  (setq L_bobysh
;;;	 (if bobyshka-OT
;;;	   80
;;;	   (point|get-L_bobysh))
;;;	)
;;;
;;;
;;;
;;;  (setq sensor-type (xlsgpar "прототип" xlsline))
;;;
;;;  (cond
;;;    ((= sensor-type "ТС-Б-У")(setq sensor-type "ТС-Б-У-Е"))
;;;    ((= sensor-type "ТП-Б-У")(setq sensor-type "ТП-Б-У-Е"))
;;;    (T (setq sensor-type
;;;	 (if (> CT_ 300)	; %%dC
;;;	   "ТП-Б-У-Е"
;;;	   "ТС-Б-У-Е"
;;;	   )
;;;	))
;;;    )
;;;  
;;;  
;;;
;;;  ;;;;;;;;;;;;;;;;;;;;;;;;;;;;;;;;;;;;;;;;;;;;;;;;;;;;;;;;;;;;;;;;;;;
;;;  ;;;;;;;;;;;;;;;;;     ДАТЧИК      ;;;;;;;;;;;;;;;;;;;;;;;;;;;;;;;;;
;;;  ;;;;;;;;;;;;;;;;;;;;;;;;;;;;;;;;;;;;;;;;;;;;;;;;;;;;;;;;;;;;;;;;;;;
;;;
;;;
;;;  (setq T_diap (point|get-tempr-scale))
;;;
;;;
;;;
;;;  (setq L_mch (point|get-nearest-L_mont))
;;;  ;;;;;;;;;;;;;;;;;;;;;;;;;;;;;;;;;;;;;;;;;;;;;;;;;;;;;;;;;;;;;;;;;;;;;;;;;;;;;;;;;;;;;;;;;;;;
;;;
;;;  (setq L_nch (point|get-nearest-L_nar))
;;;  ;(setq L_nch 120)
;;;
;;;
;;;;;;;;;;;;;;;;;;;;;;;;;;;;;;;;;;;;;;;;;;;;;;;;;;;;;;;;;;;;;;;;;;;;;;;;;;;;;;;;;;;;;;;;;;;;;;;
;;;
;;;
;;;;;;(setq diam_mch (point|get-diam-mch))
;;;
;;;  ; у ступенчатых чехлов других вариантов тут нет
;;;  (setq diam_schup 8)
;;;  (setq diam_mch 10)
;;;
;;;
;;;
;;;
;;;  ;;;;;;;;;;;;;;;;;;;;;;;;;;;;;;;;;;;;;;;;;;;;;;;;;;;;;;;;;;;;;;;;;;;
;;;  ;;;;;;;;;;;;;;;;;     ПАРАГРАФ    ;;;;;;;;;;;;;;;;;;;;;;;;;;;;;;;;;
;;;  ;;;;;;;;;;;;;;;;;;;;;;;;;;;;;;;;;;;;;;;;;;;;;;;;;;;;;;;;;;;;;;;;;;;
;;;
;;;  (setq paragraph
;;;  
;;;     (list
;;;;;;    (list
;;;;;;      "" (xlsgpar "KKS" xlsline) "" "" "" "" "" "" ""
;;;;;;      )
;;;;;;    (list
;;;;;;      "" (strcat (xlsgpar "meas_name" xlsline) ", " (xlsgpar "nom_val" xlsline) " %%dC") "" "" "" "" "" "" ""
;;;;;;      )
;;;;;;    
;;;;;;    (list
;;;;;;      (xlsgpar "Diam_tr" xlsline) "" "" "" "" "" "" "" ""
;;;;;;      )
;;;    
;;;    ;;;;;;;;;;;;;;;;;;;;;;;;;;;;;;;;;;;;;;;;;;;;;;;;;;;;;;;;;;;;;;;;;;;;;;;;;;;;;;;;;;;;;;;;;;;;
;;;    (list
;;;      ""
;;;      (strcat (cond
;;;	((= sensor-type "ТС-Б-У-Е") "Термопреобразователь сопротивления унифицированный погружной:")
;;;	((= sensor-type "ТП-Б-У-Е") "Преобразователь термоэлектрический унифицированный погружной:")
;;;	) "\n"
;;;	     "класс точности 0,5 %, диапазон измерения (0...+" (itoa T_diap) ") °C," "\n"
;;;	     "длина монтажной части " (itoa L_mch) " мм, диаметр монтажной части " (itoa diam_mch) " мм," "\n"
;;;	     "тип крепления - подвижный штуцер, длина наружной части " (itoa L_nch) " мм," "\n"
;;;	     "присоединение M20x1,5, напряжение питания 24 В, степень защиты IP65;" "\n"
;;;	      "в комплекте:"
;;;	   )
;;;      (strcat
;;;      (cond
;;;	((= sensor-type "ТС-Б-У-Е") "ТС-Б-У")
;;;	((= sensor-type "ТП-Б-У-Е") "ТП-Б-У")
;;;	)
;;;	     " (4-20)мА-(±0,5)-П-" "\n"
;;;	     "-(0..." (itoa T_diap) ")-" (itoa L_mch) "/" (itoa diam_mch) "-ПШ." (itoa L_nch) ".М20х1,5-Е" "\n"
;;;      (cond
;;;	((= sensor-type "ТС-Б-У-Е") "ТУ РБ 03 10 1826 08")
;;;	((= sensor-type "ТП-Б-У-Е") "ТУ РБ 390184271.012-2008")
;;;	)
;;;      )
;;;      ""
;;;      (strcat "ООО \"ПОИНТ\"" " " "г. Полоцк")
;;;      "шт."
;;;      (itoa kol)
;;;      ""
;;;      "Аналог"
;;;      )
;;;    
;;;    ;;;;;;;;;;;;;;;;;;;;;;;;;;;;;;;;;;;;;;;;;;;;;;;;;;;;;;;;;;;;;;;;;;;;;;;;;;;;;;;;;;;;;;;;;;;;
;;;    (list
;;;      ""
;;;      (strcat
;;;	     "Гильза цилиндрическая цельноточеная:" "\n"
;;;	     "внешний диаметр 14 мм, длина монтажной части " (itoa L_mch) " мм," "\n"
;;;	     "присоединение M20x1,5, условное давление 25 МПа, материал 12Х18Н10Т;"
;;;	     ;"Гильза цилиндрическая сварная:" "\n"
;;;	     ;"внешний диаметр 16 мм, длина монтажной части " (itoa L_mch) " мм," "\n"
;;;	     ;"присоединение M20x1,5, условное давление 25 МПа, материал 12Х18Н10Т;"      
;;;	     )
;;;      (strcat
;;;	"ГЦР.111-M20x1,5-14-"(itoa L_mch)"-25"			;цельноточеная
;;;	;"ГЦР.103-M20x1,5-16-"(itoa L_mch)"-25"			;сварная
;;;	)
;;;      ""
;;;      (strcat "ООО \"ПОИНТ\"" " " "г. Полоцк")
;;;      "шт."
;;;      (itoa kol)
;;;      ""
;;;      "Аналог"
;;;      );list
;;;
;;;    ;;;;;;;;;;;;;;;;;;;;;;;;;;;;;;;;;;;;;;;;;;;;;;;;;;;;;;;;;;;;;;;;;;;;;;;;;;;;;;;;;;;;;;;;;;;;
;;;    (list
;;;      ""
;;;      (strcat "Бобышка: L=" (itoa L_bobysh) " мм, присоединение M20x1,5")
;;;      (if bobyshka-OT
;;;	"01 ОСТ 108.530.01"
;;;	(strcat
;;;	  "1/28-" (itoa L_bobysh) "-M20x1,5"
;;;	  )
;;;	)
;;;      ""
;;;      (if bobyshka-OT "" "ООО \"ПОИНТ\" г. Полоцк") "шт." (itoa kol) "" "Аналог"
;;;      )
;;;    )
;;;	);paragraph
;;;
;;;
;;;
;;;  
;;;  (if (member D_truby '(25 32 38))		;;; нужен расширитель
;;;    (setq paragraph (reverse (cdr (reverse paragraph)))		;убрали бобышку
;;;	  paragraph
;;;	   (append paragraph (list
;;;		   
;;;	(list
;;;	  ""
;;;	  "Расширитель прямой с бобышкой, для установки приборов, 12Х18Н10Т"
;;;	  (strcat "57x" (itoa D_truby) "-M20x1,5-Б")
;;;	  "ООО \"ПОИНТ\" г. Полоцк" "шт." (itoa kol) "" ""
;;;	  )
;;;	)
;;;	))
;;;    )
;;;  paragraph
;;;  );defun
;;;;;;;;;;;;;;;;;;;;;;;;;;;;;;;;;;;;;;;;;;;;;;;;;;;;;;;;;;
;;;;;;;;;;;;;;;;;;;;;;;;;;;;;;;;;;;;;;;;;;;;;;;;;;;;;;;;;;
;;;
;;;;;; выводит список :
;;;;;;'(("" "GDK21CT001" "" "" "" "" "" "" "")
;;;;;;  ("" "Температура химочищенной воды перед подогревателем GDK21AC001, 50 %%dC" "" "" "" "" "" "" "")
;;;;;;  ("57" "" "" "" "" "" "" "" "")
;;;;;;  (""
;;;;;;   "Термопреобразователь сопротивления унифицированный погружной:\nкласс точности 0,5 %, диапазон измерения (0...+80) °C,\nдлина монтажной части 80 мм, диаметр монтажной части 10 мм,\nтип крепления - подвижный штуцер, длина наружной части 50 мм,\nприсоединение M20x1,5, напряжение питания 24 В, степень защиты IP65;\nв комплекте:"
;;;;;;    "ТС-Б-У (4-20)мА-(±0,5)-П-\n-(0...80)-80/10-ПШ.50.М20х1,5-Е\nТУ РБ 03 10 1826 08"
;;;;;;    "" "ООО \"ПОИНТ\" г. Полоцк" "шт." "1" "" "Аналог")
;;;;;;  (""
;;;;;;    "Гильза цилиндрическая цельноточеная:\nвнешний диаметр 14 мм, длина монтажной части 80 мм,\nприсоединение M20x1,5, условное давление 25 МПа, материал 12Х18Н10Т;"
;;;;;;    "ГЦР.111-M20x1,5-14-80-25" "" "ООО \"ПОИНТ\" г. Полоцк" "шт." "1" ""
;;;;;;    "Аналог")
;;;;;;  ("" "Бобышка: L=40 мм, присоединение M20x1,5" "1/28-40-M20x1,5" "" "ООО \"ПОИНТ\" г. Полоцк" "шт." "1" "" "Аналог")
;;;;;;)
;;;








;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;





;;;принимаем список:
;;;  0            1       2        3            4          5              6
;;; D_tru	nom_val max 	прототип	P	бобышка		kol
;;;("57"	"20"	"#"	"ТС-Б-У"	"0,6"	"#"		"3")

(defun gen2-komplekt-point
       			  (paramlist /
			   CP_ CT_ D_truby
			   bobyshka-OT L_bobysh
			   sensor-type T_diap L_mch L_nch diam_schup diam_mch
			   kol
			   paragraph
			   )

  

  ;;;;;;;;;;;;;;;;;;;;;;;;;;;;;;;;;;;;;;;;;;;;;;;;;;;;;;;;;;;;;;;;;;;
  ;;;;;;;;;;;;;;  выбор параметров комплекта датчика  ;;;;;;;;;;;;;;;
  ;;;;;;;;;;;;;;;;;;;;;;;;;;;;;;;;;;;;;;;;;;;;;;;;;;;;;;;;;;;;;;;;;;;
  ; CP_ МПа
  (if (and
	(setq CP_ (nth 4 paramlist))
	(isnumericstring CP_)
	)
    (setq CP_ (atof* CP_))
    (setq CP_ 0.1)
    )
  
  (setq CT_ (max (* 1.6 (atof* (nth 1 paramlist))) (* 1.2 (atof (nth 2 paramlist)))))
  (setq D_truby (atoi (nth 0 paramlist)))
  (setq kol (nth 6 paramlist))
  ;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;

  ;;;; толщина изоляци
  ;(load (strcat #lisppath "specification\\толщина изоляции.LSP")) ; ТКП45-4.02-129-2009 = list
  ;(setq dL_izo (get-closer-from-table CT_ D_truby #ТКП45-4.02-129-2009))
  ;;;;;;;;;;;;;;;;;;;;;;;;;;;;;;;;;;;;;;;;;;;;;;;;;;;;;;;;;;;;;;;;;;;;;;;;;;;;;;;;;;;;;;;;;;;;
  ;;;     по хорошему нужно учитывать для выбора составляющих
  ;;;;;;;;;;;;;;;;;;;;;;;;;;;;;;;;;;;;;;;;;;;;;;;;;;;;;;;;;;;;;;;;;;;


  ;;;;;;;;;;;;;;;;;;;;;;;;;;;;;;;;;;;;;;;;;;;;;;;;;;;;;;;;;;;;;;;;;;;
  ;;;;;;;;;;;;;;;;;     БОБЫШКА     ;;;;;;;;;;;;;;;;;;;;;;;;;;;;;;;;;
  ;;;;;;;;;;;;;;;;;;;;;;;;;;;;;;;;;;;;;;;;;;;;;;;;;;;;;;;;;;;;;;;;;;;
  
  (setq bobyshka-OT (or (> CP_ 2.6) (= "ОТ" (nth 5 paramlist))))
  
	
  (defun point|get-L_bobysh (/)
    (cond
      ((< D_truby 150) 40)
      ((>= D_truby 150) 80)
      )
    );defun
  (setq L_bobysh
	 (if bobyshka-OT
	   LBD40CT001
	   80
	   (point|get-L_bobysh))
	)



  (setq sensor-type (nth 3 paramlist))

  (cond
    ((= sensor-type "ТС-Б-У")(setq sensor-type "ТС-Б-У-Е"))
    ((= sensor-type "ТП-Б-У")(setq sensor-type "ТП-Б-У-Е"))
    (T (setq sensor-type
	 (if (> CT_ 300)	; %%dC
	   "ТП-Б-У-Е"
	   "ТС-Б-У-Е"
	   )
	))
    )
  
  

  ;;;;;;;;;;;;;;;;;;;;;;;;;;;;;;;;;;;;;;;;;;;;;;;;;;;;;;;;;;;;;;;;;;;
  ;;;;;;;;;;;;;;;;;     ДАТЧИК      ;;;;;;;;;;;;;;;;;;;;;;;;;;;;;;;;;
  ;;;;;;;;;;;;;;;;;;;;;;;;;;;;;;;;;;;;;;;;;;;;;;;;;;;;;;;;;;;;;;;;;;;

  (defun point|get-tempr-scale (/ lst)
    (cond
      ((= sensor-type "ТП-Б-У-Е") (setq lst '(600 700 800 900)))
      ((= sensor-type "ТС-Б-У-Е") (setq lst '(50 80 100 150 180 200 250 300 400 500)))
      );defun
    (get-closer-from-row CT_ lst)
    );defun
  (setq T_diap (point|get-tempr-scale))


  (defun point|get-nearest-L_mont (/ lst condidatelist Lmch_min Lmch_max)
    (setq Lmch_min (+ (/ D_truby 3.0) L_bobysh))
    (setq Lmch_max (+ (/ D_truby 1.8) L_bobysh))
    (cond
      ((= sensor-type "ТП-Б-У-Е") (setq lst '(120 160 200 250 320 400 500 630 800 1000 1600 2000 2500 3150)))
      ((= sensor-type "ТС-Б-У-Е") (setq lst '(80 100 120 160 200 250 320 400 500 630 800 1000 1250 1600 2000 2500 3150)))
      )
    (setq condidatelist
	 (vl-remove-if
	   '(lambda (x)
	      (or
		(< x Lmch_min)
		(> x Lmch_max)
		)) lst))
    (if condidatelist
      (eval (append '(min) condidatelist))
      (eval (append '(min) lst))	;временная мера изза гребаных технологов с трубой 57 на 400 градусах
;;;      (if (< D_truby (- (car lst)  L_bobysh))
;;;	(alert "слишком тонкая труба и короткая бобышка\nнет такой длины монтажной части")
;;;	(car lst)
;;;	)
      )
  );defun
  (setq L_mch (point|get-nearest-L_mont))
  ;;;;;;;;;;;;;;;;;;;;;;;;;;;;;;;;;;;;;;;;;;;;;;;;;;;;;;;;;;;;;;;;;;;;;;;;;;;;;;;;;;;;;;;;;;;;
  (defun point|get-nearest-L_nar ( / tmp)
    (setq tmp (* T_diap 1.1))
    (cond
      ((diap tmp -100 399) 50)
      ((diap tmp 0    799) 120)
      ((diap tmp 800 1000) 160)
      ((> tmp        1000) 200)
      )
    );defun
  (setq L_nch (point|get-nearest-L_nar))
  ;(setq L_nch 120)


;;;;;;;;;;;;;;;;;;;;;;;;;;;;;;;;;;;;;;;;;;;;;;;;;;;;;;;;;;;;;;;;;;;;;;;;;;;;;;;;;;;;;;;;;;;;

;;;  (defun point|get-diam-mch ( / tmp)
;;;    (setq tmp (* L_mch 1.1))
;;;    (cond
;;;      ;((diap tmp 0 320) 6)
;;;      ((diap tmp 0 1000) 8)
;;;      (T 10)
;;;      )
;;;    )
;;;(setq diam_mch (point|get-diam-mch))

  ; у ступенчатых чехлов других вариантов тут нет
  (setq diam_schup 8)
  (setq diam_mch 10)




  ;;;;;;;;;;;;;;;;;;;;;;;;;;;;;;;;;;;;;;;;;;;;;;;;;;;;;;;;;;;;;;;;;;;
  ;;;;;;;;;;;;;;;;;     ПАРАГРАФ    ;;;;;;;;;;;;;;;;;;;;;;;;;;;;;;;;;
  ;;;;;;;;;;;;;;;;;;;;;;;;;;;;;;;;;;;;;;;;;;;;;;;;;;;;;;;;;;;;;;;;;;;

  (setq paragraph
  
     (list
   
    ;;;;;;;;;;;;;;;;;;;;;;;;;;;;;;;;;;;;;;;;;;;;;;;;;;;;;;;;;;;;;;;;;;;;;;;;;;;;;;;;;;;;;;;;;;;;
    (list
      ""
      (strcat (cond
	((= sensor-type "ТС-Б-У-Е") "Термопреобразователь сопротивления унифицированный погружной:")
	((= sensor-type "ТП-Б-У-Е") "Преобразователь термоэлектрический унифицированный погружной:")
	) "\n"
	     "класс точности 0,5 %, диапазон измерения (0...+" (itoa T_diap) ") °C," "\n"
	     "длина монтажной части " (itoa L_mch) " мм, диаметр монтажной части " (itoa diam_mch) " мм," "\n"
	     "тип крепления - подвижный штуцер, длина наружной части " (itoa L_nch) " мм," "\n"
	     "присоединение M20x1,5, напряжение питания 24 В, степень защиты IP65;" "\n"
	      "в комплекте:"
	   )
      (strcat
      (cond
	((= sensor-type "ТС-Б-У-Е") "ТС-Б-У")
	((= sensor-type "ТП-Б-У-Е") "ТП-Б-У")
	)
	     " (4-20)мА-(±0,5)-П-" "\n"
	     "-(0..." (itoa T_diap) ")-" (itoa L_mch) "/" (itoa diam_mch) "-ПШ." (itoa L_nch) ".М20х1,5-Е" "\n"
      (cond
	((= sensor-type "ТС-Б-У-Е") "ТУ РБ 03 10 1826 08")
	((= sensor-type "ТП-Б-У-Е") "ТУ РБ 390184271.012-2008")
	)
      )
      ""
      (strcat "ООО \"ПОИНТ\"" " " "г. Полоцк")
      "шт."
      kol
      ""
      "Аналог"
      )
    
    ;;;;;;;;;;;;;;;;;;;;;;;;;;;;;;;;;;;;;;;;;;;;;;;;;;;;;;;;;;;;;;;;;;;;;;;;;;;;;;;;;;;;;;;;;;;;
    (list
      ""
      (strcat
	     "Гильза цилиндрическая цельноточеная:" "\n"
	     "внешний диаметр 14 мм, длина монтажной части " (itoa L_mch) " мм," "\n"
	     ;;;;  обратить внимание , 14- Ду 16
	     "присоединение M20x1,5, условное давление 25 МПа, материал 12Х18Н10Т;"
	     ;"Гильза цилиндрическая сварная:" "\n"
	     ;"внешний диаметр 16 мм, длина монтажной части " (itoa L_mch) " мм," "\n"
	     ;"присоединение M20x1,5, условное давление 25 МПа, материал 12Х18Н10Т;"      
	     )
      (strcat
	"ГЦР.111-M20x1,5-14-"(itoa L_mch)"-25"			;цельноточеная
	;"ГЦР.103-M20x1,5-16-"(itoa L_mch)"-25"			;сварная
	)
      ""
      (strcat "ООО \"ПОИНТ\"" " " "г. Полоцк")
      "шт."
      kol
      ""
      "Аналог"
      );list

    ;;;;;;;;;;;;;;;;;;;;;;;;;;;;;;;;;;;;;;;;;;;;;;;;;;;;;;;;;;;;;;;;;;;;;;;;;;;;;;;;;;;;;;;;;;;;
    (list
      ""
      (strcat "Бобышка: L=" (itoa L_bobysh) " мм, присоединение M20x1,5")
      (if bobyshka-OT
	"01 ОСТ 108.530.01"
	(strcat
	  "1/28-" (itoa L_bobysh) "-M20x1,5"
	  )
	)
      ""
      (if bobyshka-OT "" "ООО \"ПОИНТ\" г. Полоцк") "шт." kol "" "Аналог"
      )
    )
	);paragraph



  
  (if (member D_truby '(25 32 38))
    (setq paragraph (reverse (cdr (reverse paragraph)))		;убрали бобышку
	  paragraph
	   (append paragraph (list
		   
	(list
	  ""
	  "Расширитель прямой с бобышкой, для установки приборов, 12Х18Н10Т"
	  (strcat "57x" (itoa D_truby) "-M20x1,5-Б")
	  ""
	  "ООО \"ПОИНТ\" г. Полоцк" "шт." kol "" ""
	  )
	)
	))
    )
  paragraph
  );defun
