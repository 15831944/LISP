(tbl|getdata 't:data)


(db|getdata 'db:head 'db:data)
(length db:data)

(setq odnames (excel>lst))
;'(("2" "Перечень условных обозначений") ("3" "Паропроводы турбины") ("4" "Температурный контроль металла подшипников турбины и генератора") ("5" "Контроль вибрации и мехвеличин") ("6" "Конденсационная система и эжекторные установки") ("7" "Система регенирации низкого и высокого давления") ("8" "Система подогрева сетевой воды через ПСГ") ("9" "Система охлаждения") ("10" "Температурный контроль\\Pгенератора") ("11" "Система маслоснабжения подшипников турбины") ("12" "Система маслоснабжения\\Pуплотнений вала генератора") ("13" "Система маслоснабжения\\Pподшипников СН-6А") ("14" "Система маслоснабжения\\Pподшипников СН-6Б") ("15" "Система маслоснабжения\\Pподшипников СН-6В") ("16" "Питательный насос ПЭН-7") ("17" "Питательный насос ПЭН-8") ("18" "Питательный насос ПЭН-9") ("19" "Тракт сетевой воды") ("20" "Деаэрационная установка "))
(setq odnames '(
		("2" "Перечень условных обозначений")
		("3" "Паропроводы турбины")
		("4" "Температурный контроль металла подшипников турбины и генератора")
		("5" "Контроль вибрации и мехвеличин")
		("6" "Конденсационная система и эжекторные установки")
		("7" "Система регенирации низкого и высокого давления")
		("8" "Система подогрева сетевой воды через ПСГ")
		("9" "Система охлаждения")
		("10" "Температурный контроль\\Pгенератора")
		("11" "Система маслоснабжения подшипников турбины")
		("12" "Система маслоснабжения\\Pуплотнений вала генератора")
		("13" "Система маслоснабжения\\Pподшипников СН-6А")
		("14" "Система маслоснабжения\\Pподшипников СН-6Б")
		("15" "Система маслоснабжения\\Pподшипников СН-6В")
		("16" "Питательный насос ПЭН-7")
		("17" "Питательный насос ПЭН-8")
		("18" "Питательный насос ПЭН-9")
		("19" "Тракт сетевой воды")
		("20" "Деаэрационная установка ")
		))

(lst>excel odnames)


(setq z1data (db|mapzip db:data "PID"))

(setq z1data (vl-remove (assoc "" (cdr z1data)) z1data))

(setq tmp
(vl-sort
  (cdr z1data)
  '(lambda (a b)
     (<
       (atof* (cadr (sepstr (car a) " л.")))
       (atof* (cadr (sepstr (car b) " л.")))
       )
     )
  ))

(setq z1data (cons "table" tmp))


(setq result
       
(mapcar
  '(lambda (drw / name )	;(setq drw (nth 2 z1data))
     (setq name (cadr (assoc (cadr (sepstr (car drw) " л."))odnames)))
     (cons
       (list (strcat "PI-диаграмма " (car drw) " " name))
       (mapcar
	 '(lambda (line)	;(setq line (nth 3 drw))

	    (list
	      (strcat (db|gpar "KKS" line) "\n" (db|gpar "st_POZ" line))
	      (db|gpar "name" line)
	      (strcat (db|gpar "Привод" line) "\n" (db|gpar "fr" line))
	      (strcat "380" "\n" (db|gpar "N" line))
	      (db|gpar "t1" line)
	      (db|gpar "t2" line)
	      ""
	      (strcat "98-13-ТИ-ИОС.АТХ.СБ-ТО л." (db|gpar "8elsch" line))
	      (strcat (db|gpar "$pnl" line) "-" (db|gpar "$cab" line))
	      (strcat "98-13-ТИ-ИОС.АТХ.СБ-ТО л." (db|gpar "8elsch" line) ".2")
	      
	      )
	    
	    )
	 (cdr drw)
	 )
       )
     )
  (cdr z1data)
  )
      )


(lst>excel (apply 'append result))
