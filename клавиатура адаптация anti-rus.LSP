(defun c:çå () (command "pt"))
(defun c:çà () (command "pf"))


(defun c:tr () (command "_trim"))
(defun c:åê () (command "_trim"))
(defun c:f () (command "_fillet"))
(defun c:à () (command "_fillet"))
(defun c:ch () (command "_chamber"))
(defun c:ñð () (command "_chamber"))
(defun c:j () (command "_join"))
(defun c:î () (command "_join"))
