;;;; 13_05_01
;;;;;;;; надо допиливать причем трудоемко
;(load (strcat #lisppath "strings/editmark.lsp"))

(setq str "NDА12AP001")

(defun isstringKKS (str / frmt)
  (setq frmt (getmarkformat str))
  (cond
    ((equal
       '("eng" "eng" "eng" "num" "num" "eng" "eng" "num" "num" "num")
       (getmarkformat "NDА12AP001")
       )
     T)
    ()
    )
  );defun



;(lst>excel (mapcar '(lambda (x) (sepstr* (car x))) (excel>lst)))
